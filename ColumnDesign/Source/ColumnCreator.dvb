Attribute VB_Name = "AutoName"
Public Function AutoSheetName()
    'Gates columns
    ColumnCreator.ProjectNameBox.Value = ConvertToNum(ColumnCreator.WidthBox.Value) & """ x " & ConvertToNum(ColumnCreator.LengthBox.Value) & """" & " GATES COLUMN FORM"
    
    'Scissor clamp columns
    ColumnCreator.sProjectNameBox.Value = ConvertToNum(ColumnCreator.sWidthBox.Value) & """ x " & ConvertToNum(ColumnCreator.sLengthBox.Value) & """" & " SCISSOR CLAMP COLUMN FAB"
End Function

Attribute VB_Name = "CalcWeight_Function"
'Calculates weight of 1 given column from ply, studs, clamps, and braces (only 7-11 and 11-19 braces).
'Then 50 lbs is added and that total is rounded up to the nearest 100 lbs.

Option Explicit
    'Define weights, public constants may be used anywhere
    Public Const wt_ply As Double = 2.2         'psf
    Public Const wt_2x4 As Double = 1.31        'lb/ft
    Public Const wt_LVL As Double = 1.8        'lb/ft ????????????????????????????????????? what is LVL linear weight
    Public Const wt_08_24_clamp As Double = 76  'lbs
    Public Const wt_12_36_clamp As Double = 100 'lbs
    Public Const wt_24_48_clamp As Double = 123 'lbs
    Public Const wt_36_scissor_clamp As Double = 40 'lbs
    Public Const wt_48_scissor_clamp As Double = 56 'lbs
    Public Const wt_60_scissor_clamp As Double = 85 'lbs
    Public Const wt_07_11_brace As Double = 52  'lbs
    Public Const wt_11_19_brace As Double = 76  'lbs
    Public Const wt_extra As Double = 50        'lbs
    
    
Function wt_total(x, y, z, n_studs_x, n_studs_y, stud_type, n_clamps, clamp_size, brace_size) As Double

    Dim wt_stud As Double
    Dim wt_clamp As Double
    Dim wt_brace As Double
    
'Pick weights based on stud type, clamp size, and brace size
    Select Case stud_type
        Case Is = 1
            wt_stud = wt_2x4
        Case Is = 2
            wt_stud = wt_LVL
        Case Else
            MsgBox ("Error: Invalid stud type detected in weight calculation")
    End Select
    
    Select Case clamp_size
        Case Is = 1
            wt_clamp = wt_08_24_clamp
        Case Is = 2
            wt_clamp = wt_12_36_clamp
        Case Is = 3
            wt_clamp = wt_24_48_clamp
        Case Is = 4
            wt_clamp = wt_36_scissor_clamp
        Case Is = 5
            wt_clamp = wt_48_scissor_clamp
        Case Is = 6
            wt_clamp = wt_60_scissor_clamp
        Case Else
            MsgBox ("Error: Invalid clamp size detected in weight calculation")
    End Select
    
    Select Case brace_size
        Case Is = 0
            wt_brace = 0
        Case Is = 1
            wt_brace = wt_07_11_brace
        Case Is = 2
            wt_brace = wt_11_19_brace
        Case Else
            MsgBox ("Error: Invalid brace size detected in weight calculation")
    End Select
    
    'Sum weights
    wt_total = _
    wt_ply * (((x + 2.25) * z * 2 / 144) + ((y + 2.25) * z * 2 / 144)) + _
    wt_stud * (z / 12) * 2 * (n_studs_x + n_studs_y) + _
    wt_clamp * n_clamps + _
    wt_brace * 3
    
    'Add 50 lbs and round up to the nearest 100
    wt_total = ColumnCreator.RoundUp((wt_total + wt_extra) / 100)
    wt_total = wt_total * 100
    
End Function


Function wt_panel(x, y, z, n_studs_x, n_studs_y, stud_type) As Double
'This function is for calculating the weight of one side of the column form.
    Dim wt_stud As Double
    Dim larger_side As Double
    Dim most_studs As Double
    
'Pick weights based on stud type, clamp size, and brace size
    Select Case stud_type
        Case Is = 1
            wt_stud = wt_2x4
        Case Is = 2
            wt_stud = wt_LVL
        Case Else
            MsgBox ("Error: Invalid stud type detected in weight calculation")
    End Select
    
    'Find if x or y side is larger
    If x > y Then
        larger_side = x
    Else
        larger_side = y
    End If
    
    'Find out if the x or y side has more studs
    If n_studs_x > n_studs_y Then
        most_studs = n_studs_x
    Else
        most_studs = n_studs_y
    End If
    
    'Sum weights
    wt_panel = _
    wt_ply * ((larger_side + 4.5) * z / 144) + _
    wt_stud * (z / 12) * most_studs
    
    'Increase weight by 10% and round it up to the nearest 10 pounds
    wt_panel = ColumnCreator.RoundUp((wt_panel * 1.1) / 10)
    wt_panel = wt_panel * 10

    
    
End Function

Attribute VB_Name = "CheckInputs_Function"
Public Function CheckInputs(ByVal x, ByVal y, ByVal z, ByVal qty As Double, qtyCheck As Integer) As Integer
    'Check that all inputs are within defined bounds NOTE: Change this to 2read limits from the data files
    'qtyCheck = 0 means the quantity box is not considered
    
    Dim min_width As Integer
    Dim min_length As Integer
    Dim min_height As Integer
    Dim max_width As Integer
    Dim max_length As Integer
    Dim max_height As Integer
        
    If ColumnCreator.MultiPage1.Value = 0 Then
' # # # # # # # # # # # # # # # # # # # # # # # # # # # #
'                    GATES COLUMNS
' # # # # # # # # # # # # # # # # # # # # # # # # # # # #

        'Define maximum column dimensions
        min_width = 12
        min_length = 12
        min_height = 96
        max_width = 48
        max_length = 48
        max_height = 240
        
        'Assume checks will pass
        CheckInputs = 1
        
        'If any check fails it will not pass
        If Round(x, 3) < min_width Then
            CheckInputs = 0
        ElseIf Round(x, 3) > max_width Then
            CheckInputs = 0
        End If
    
        If Round(y, 3) < min_length Then
            CheckInputs = 0
        ElseIf Round(y, 3) > max_length Then
            CheckInputs = 0
        End If
        
        If Round(z, 3) < min_height Then
            CheckInputs = 0
        ElseIf Round(z, 3) > max_height Then
            CheckInputs = 0
        End If
        
        If qtyCheck = 1 And qty = 0 Then
            CheckInputs = 0
        End If
        
        'Control the background colors to indicate when an entered value is out of bounds (without passing or failing the check)

        If Round(x, 3) < min_width And x <> 0 Then
            ColumnCreator.WidthBox.BackColor = &H8080FF
        ElseIf Round(x, 3) > max_width And x <> 0 Then
            ColumnCreator.WidthBox.BackColor = &H8080FF
        Else
            ColumnCreator.WidthBox.BackColor = &H80000005
        End If
        
        If Round(y, 3) < min_length And y <> 0 Then
            ColumnCreator.LengthBox.BackColor = &H8080FF
        ElseIf Round(y, 3) > max_length And y <> 0 Then
            ColumnCreator.LengthBox.BackColor = &H8080FF
        Else
            ColumnCreator.LengthBox.BackColor = &H80000005
        End If
        
        If Round(z, 3) < min_height And z <> 0 Then
            ColumnCreator.HeightBox.BackColor = &H8080FF
        ElseIf Round(z, 3) > max_height And z <> 0 Then
            ColumnCreator.HeightBox.BackColor = &H8080FF
        Else
            ColumnCreator.HeightBox.BackColor = &H80000005
        End If
        
        
        
    
    ElseIf ColumnCreator.MultiPage1.Value = 1 Then
' # # # # # # # # # # # # # # # # # # # # # # # # # # # #
'                 SCISSOR CLAMP COLUMNS
' # # # # # # # # # # # # # # # # # # # # # # # # # # # #

        'Define maximum column dimensions
        min_width = 8
        min_length = 8
        min_height = 12
        max_width = 46
        max_length = 46
        max_height = 480 ' 40'-0" (10 4' tall plywood sheets is 1 under the plywood drawing limit)
        
        'Assume checks will pass
        CheckInputs = 1
        
        'If any check fails it will not pass
        If Round(x, 3) < min_width Then
            CheckInputs = 0
            ColumnCreator.slblMaxHt.Caption = "N/A"
        ElseIf Round(x, 3) > max_width Then
            CheckInputs = 0
        End If
    
        If Round(y, 3) < min_length Then
            CheckInputs = 0
            ColumnCreator.slblMaxHt.Caption = "N/A"
        ElseIf Round(y, 3) > max_length Then
            CheckInputs = 0
        End If
        
        If Round(z, 3) < min_height Then
            CheckInputs = 0
        ElseIf Round(z, 3) > max_height Then
            CheckInputs = 0
        End If
        
        If qtyCheck = 1 And qty = 0 Then
            CheckInputs = 0
        End If
        
        'Control the background colors to indicate when an entered value is out of bounds (without passing or failing the check)

        If Round(x, 3) < min_width And x <> 0 Then
            ColumnCreator.sWidthBox.BackColor = &H8080FF
        ElseIf Round(x, 3) > max_width And x <> 0 Then
            ColumnCreator.sWidthBox.BackColor = &H8080FF
        Else
            ColumnCreator.sWidthBox.BackColor = &H80000005
        End If
        
        If Round(y, 3) < min_length And y <> 0 Then
            ColumnCreator.sLengthBox.BackColor = &H8080FF
        ElseIf Round(y, 3) > max_length And y <> 0 Then
            ColumnCreator.sLengthBox.BackColor = &H8080FF
        Else
            ColumnCreator.sLengthBox.BackColor = &H80000005
        End If
        
        If Round(z, 3) < min_height And z <> 0 Then
            ColumnCreator.sHeightBox.BackColor = &H8080FF
        ElseIf Round(z, 3) > max_height And z <> 0 Then
            ColumnCreator.sHeightBox.BackColor = &H8080FF
        Else
            ColumnCreator.sHeightBox.BackColor = &H80000005
        End If
        
    End If
End Function

Attribute VB_Name = "Collection_Function"
Public Function BuildCollection() As Collection
    'Create collection of image objects for drawing the elevation view
    
    Dim Coll As Collection
    Set Coll = New Collection
    
    If ColumnCreator.MultiPage1.Value = 0 Then
' # # # # # # # # # # # # # # # # # # # # # # # # # # # #
'                    GATES COLUMNS
' # # # # # # # # # # # # # # # # # # # # # # # # # # # #
        Coll.Add ColumnCreator.img_line_4   'Item #1
        Coll.Add ColumnCreator.img_line_5
        Coll.Add ColumnCreator.img_line_6
        Coll.Add ColumnCreator.img_line_7
        Coll.Add ColumnCreator.img_line_8
        Coll.Add ColumnCreator.img_line_9
        Coll.Add ColumnCreator.img_line_10
        Coll.Add ColumnCreator.img_line_11
        Coll.Add ColumnCreator.img_line_12
        Coll.Add ColumnCreator.img_line_13
        Coll.Add ColumnCreator.txt_1        'Item #11
        Coll.Add ColumnCreator.txt_2
        Coll.Add ColumnCreator.txt_3
        Coll.Add ColumnCreator.txt_4
        Coll.Add ColumnCreator.txt_5
        Coll.Add ColumnCreator.txt_6
        Coll.Add ColumnCreator.txt_7
        Coll.Add ColumnCreator.txt_8
        Coll.Add ColumnCreator.txt_9
        Coll.Add ColumnCreator.txt_10
        Coll.Add ColumnCreator.txt_11
    ElseIf ColumnCreator.MultiPage1.Value = 1 Then
' # # # # # # # # # # # # # # # # # # # # # # # # # # # #
'                 SCISSOR CLAMP COLUMNS
' # # # # # # # # # # # # # # # # # # # # # # # # # # # #
        Coll.Add ColumnCreator.s_img_line_4   'Item #1
        Coll.Add ColumnCreator.s_img_line_5
        Coll.Add ColumnCreator.s_img_line_6
        Coll.Add ColumnCreator.s_img_line_7
        Coll.Add ColumnCreator.s_img_line_8
        Coll.Add ColumnCreator.s_img_line_9
        Coll.Add ColumnCreator.s_img_line_10
        Coll.Add ColumnCreator.s_img_line_11
        Coll.Add ColumnCreator.s_img_line_12
        Coll.Add ColumnCreator.s_img_line_13
        Coll.Add ColumnCreator.s_txt_1        'Item #11
        Coll.Add ColumnCreator.s_txt_2
        Coll.Add ColumnCreator.s_txt_3
        Coll.Add ColumnCreator.s_txt_4
        Coll.Add ColumnCreator.s_txt_5
        Coll.Add ColumnCreator.s_txt_6
        Coll.Add ColumnCreator.s_txt_7
        Coll.Add ColumnCreator.s_txt_8
        Coll.Add ColumnCreator.s_txt_9
        Coll.Add ColumnCreator.s_txt_10
        Coll.Add ColumnCreator.s_txt_11
    End If
    
    Set BuildCollection = Coll
    
End Function

Attribute VB_Name = "ColumnCreator"
Attribute VB_Base = "0{05084A41-DCCF-40E6-A00A-8A9DB0E275E7}{1A9041EC-BD58-49FF-9DB6-BAB9479A9F5D}"
Attribute VB_GlobalNameSpace = False
Attribute VB_Creatable = False
Attribute VB_PredeclaredId = True
Attribute VB_Exposed = False
Attribute VB_TemplateDerived = False
Attribute VB_Customizable = False
' TO DO LIST
' Consider using two different sized clamps on high aspect ratio columns
' Add a reverse button to the plywood layout


'All units in inches and pounds

Private Sub Userform_UI()
    If ClampSizeButton1.Value = True Then
        ClampSizeButton2.Value = False
        ClampSizeButton3.Value = False
        ClampSizeButton4.Value = False
    ElseIf ClampSizeButton2.Value = True Then
        ClampSizeButton1.Value = False
        ClampSizeButton3.Value = False
        ClampSizeButton4.Value = False
    ElseIf ClampSizeButton3.Value = True Then
        ClampSizeButton1.Value = False
        ClampSizeButton2.Value = False
        ClampSizeButton4.Value = False
    ElseIf ClampSizeButton4.Value = True Then
        ClampSizeButton1.Value = False
        ClampSizeButton2.Value = False
        ClampSizeButton3.Value = False
    End If
End Sub


Private Sub btnRotate_Click()
    If txtViewName.Caption = "Front" Then
        txtViewName.Caption = "Left"
    ElseIf txtViewName.Caption = "Left" Then
        txtViewName.Caption = "Back"
    ElseIf txtViewName.Caption = "Back" Then
        txtViewName.Caption = "Right"
    ElseIf txtViewName.Caption = "Right" Then
        txtViewName.Caption = "Front"
    End If
    
End Sub


Private Sub boxPlySeams_KeyUp(ByVal KeyAscii As MSForms.ReturnInteger, ByVal Shift As Integer)
    Call UpdatePly.UpdatePly(1)
End Sub
Private Sub boxPlySeams_KeyPress(ByVal KeyAscii As MSForms.ReturnInteger)
    If KeyAscii = 27 Then ColumnCreator.Hide
End Sub

Private Sub chkWinX_Click()
    'MsgBox chkWinX.Value
    If chkWinY.Value = True Then
        chkWinY.Value = False
        chkWinX.Value = True
    End If
    
    If chkWinX.Value = True Or chkWinY.Value = True Then
        SquaringCornerOptionRegularButton.Value = True
        SquaringCornerOptionPickingButton.Enabled = False
    End If
    
    If chkWinX.Value = False And chkWinY.Value = False Then
        SquaringCornerOptionPickingButton.Enabled = True
    End If
    
    lblAxis.Caption = "X" 'Change axis to X for this window
    Call UpdatePly.UpdatePly(2) 'Update the plywood layout sketch
End Sub
Private Sub chkWinY_Click()
    'MsgBox chkWinY.Value
    If chkWinX.Value = True Then
        chkWinX.Value = False
        chkWinY.Value = True
    End If
    
    If chkWinX.Value = True Or chkWinY.Value = True Then
        SquaringCornerOptionRegularButton.Value = True
        SquaringCornerOptionPickingButton.Enabled = False
    End If
    
    If chkWinX.Value = False And chkWinY.Value = False Then
        SquaringCornerOptionPickingButton.Enabled = True
    End If
    
    lblAxis.Caption = "Y" 'Change axis to Y for this window
    Call UpdatePly.UpdatePly(2) 'Update the plywood layout sketch
End Sub

Private Sub Image2_Click()
    If ColumnCreator.lblAxis.Caption = "X" Then
        ColumnCreator.lblAxis.Caption = "Y"
    ElseIf ColumnCreator.lblAxis.Caption = "Y" Then
        ColumnCreator.lblAxis.Caption = "X"
    End If
End Sub

Private Sub Image3_Click()
    If ColumnCreator.lblAxis.Caption = "X" Then
        ColumnCreator.lblAxis.Caption = "Y"
    ElseIf ColumnCreator.lblAxis.Caption = "Y" Then
        ColumnCreator.lblAxis.Caption = "X"
    End If
    Call UpdatePly.UpdatePly(0) 'Update the plywood layout sketch
End Sub

Private Sub Label26_Click()
    If ColumnCreator.lblAxis.Caption = "X" Then
        ColumnCreator.lblAxis.Caption = "Y"
    ElseIf ColumnCreator.lblAxis.Caption = "Y" Then
        ColumnCreator.lblAxis.Caption = "X"
    End If
    Call UpdatePly.UpdatePly(0) 'Update the plywood layout sketch
End Sub

Private Sub lblAxis_Click()
    If ColumnCreator.lblAxis.Caption = "X" Then
        ColumnCreator.lblAxis.Caption = "Y"
    ElseIf ColumnCreator.lblAxis.Caption = "Y" Then
        ColumnCreator.lblAxis.Caption = "X"
    End If
    Call UpdatePly.UpdatePly(0) 'Update the plywood layout sketch
End Sub

Private Sub MultiPage1_Change()

End Sub

Private Sub WinDim1_KeyUp(ByVal KeyAscii As MSForms.ReturnInteger, ByVal Shift As Integer)
    WinDim2.Value = ConvertFtIn(ConvertToNum(HeightBox.Value) - ConvertToNum(WinDim1.Value))
    Call UpdatePly.UpdatePly(2) 'Update the plywood layout sketch
End Sub
Private Sub WinDim2_KeyUp(ByVal KeyAscii As MSForms.ReturnInteger, ByVal Shift As Integer)
    WinDim1.Value = ConvertFtIn(ConvertToNum(HeightBox.Value) - ConvertToNum(WinDim2.Value))
    Call UpdatePly.UpdatePly(2) 'Update the plywood layout sketch
End Sub


Private Sub CommandButton2_Click()
    'Call scissor clamp module
    Call CreateScissorClamp
End Sub

Private Sub CommandButton1_Click()
    'Use error handler
    'on error GoTo ErrorHandler
    
    ColumnCreator.Hide 'Hide GUI form after clicking this command button
    
    'Referenced files are found within this folder, easier to change this partial path
    Dim FileLocationPrefix As String
    'FileLocationPrefix = "Z:\Shared\NCA\Users\Quincy\VBA\"
    FileLocationPrefix = "D:\Rider projects\ColumnDesign\ColumnDesign\Source\"
    
    'Ensure inputs are actually provided
    If ColumnCreator.WidthBox.Value = "" Or ColumnCreator.LengthBox.Value = "" Or ColumnCreator.HeightBox.Value = "" Or ColumnCreator.QuantityBox.Value = "" Then
        MsgBox ("Error: missing input")
        ColumnCreator.show
        Exit Sub
    End If

    If chkWinX.Value = True Or chkWinY.Value = True Then
        If ConvertToNum(WinDim1.Value) = 0 Or ConvertToNum(WinDim2.Value) = 0 Then
            MsgBox ("Error: Window position cannot be 0")
            ColumnCreator.show
            Exit Sub
        End If
    End If

    'Define layers, assign colors, assign linetypes
    Dim LayerObj As AcadLayer 'Creates layer object
    Dim color As AcadAcCmColor
    Dim version As String
    Dim col_ver_str As String
    'on error Resume Next
        version = ThisDrawing.Application.version
        version = Mid(version, 1, 2) 'Records the first 2 characters in the string as the version number
        col_ver_str = "AutoCAD.AcCmColor." & version
        Set color = AcadApplication.GetInterfaceObject(col_ver_str) 'Use version number to set color object

        color.ColorIndex = 154:     Set LayerObj = ThisDrawing.Layers.Add("DIM"):       LayerObj.TrueColor = color:    LayerObj.Linetype = "Continuous"
        color.ColorIndex = acRed:   Set LayerObj = ThisDrawing.Layers.Add("ELEV"):      LayerObj.TrueColor = color:    LayerObj.Linetype = "Continuous"
        color.ColorIndex = acCyan:  Set LayerObj = ThisDrawing.Layers.Add("FMTEXTA"):   LayerObj.TrueColor = color:    LayerObj.Linetype = "Continuous"
        color.ColorIndex = acBlue:  Set LayerObj = ThisDrawing.Layers.Add("FORM"):      LayerObj.TrueColor = color:    LayerObj.Linetype = "Continuous"
        color.ColorIndex = acBlue:  Set LayerObj = ThisDrawing.Layers.Add("NOTES"):     LayerObj.TrueColor = color:    LayerObj.Linetype = "Continuous"
        color.ColorIndex = acCyan:  Set LayerObj = ThisDrawing.Layers.Add("PLYA"):      LayerObj.TrueColor = color:    LayerObj.Linetype = "Continuous"
        color.ColorIndex = 23:      Set LayerObj = ThisDrawing.Layers.Add("SHADE"):     LayerObj.TrueColor = color:    LayerObj.Linetype = "Continuous"
        color.ColorIndex = acBlue:  Set LayerObj = ThisDrawing.Layers.Add("STEEL"):     LayerObj.TrueColor = color:    LayerObj.Linetype = "Continuous"
    'on error GoTo ErrorHandler
    
    'Check if any of the used layers are locked, remember which are locked, then unlock them
    Dim UsedLayerList(1 To 8) As String ' fill with used layers
    Dim LockedLayerList(1 To 8) As Integer 'leave at default values of 0, change to 1 for locked layers
    Dim FrozenLayerList(1 To 8) As Integer 'leave at default values of 0, change to 1 for frozen layers
    Dim InvisLayerList(1 To 8) As Integer 'leave at default values of 0, change to 1 for invisible layers
    UsedLayerList(1) = "DIM": UsedLayerList(2) = "ELEV": UsedLayerList(3) = "FMTEXTA": UsedLayerList(4) = "FORM": UsedLayerList(5) = "NOTES":
    UsedLayerList(6) = "PLYA": UsedLayerList(7) = "SHADE": UsedLayerList(8) = "STEEL":

    For i = 1 To UBound(UsedLayerList)
        Set LayerObj = ThisDrawing.Layers(UsedLayerList(i))
        If LayerObj.Lock = True Then
            LayerObj.Lock = False
            LockedLayerList(i) = 1
        End If
        If LayerObj.Freeze = True Then
            LayerObj.Freeze = False
            FrozenLayerList(i) = 1
        End If
        If LayerObj.LayerOn = False Then
            InvisLayerList(i) = 1
        End If
    Next i
    
    'Make new dim style, text style, and layers
    Dim OldDimStyle As AcadDimStyle
    Dim OldTextStyle As AcadTextStyle
    Dim OldLayer As AcadLayer
    
    Set OldDimStyle = ThisDrawing.ActiveDimStyle
    Set OldTextStyle = ThisDrawing.ActiveTextStyle
    Set OldLayer = ThisDrawing.ActiveLayer
    
    Call BuildColumnStyles
    
    'Define various column parameters
    Dim x As Double
    Dim y As Double
    Dim z As Double
    Dim n_col As Integer
    Dim n_studs_x As Integer 'Number of studs on the "x" side
    Dim n_studs_y As Integer 'Number of studs on the "y" side
    Dim n_clamps As Integer: n_clamps = 0 'Initialize
    Dim n_top_clamps As Integer 'Number of clamps designated "TOP CLAMPS"
    Dim n_reinf_angles As Integer 'Number of Gates Reinforcing Angles (apply to clamps below the top 87" when any column side is over 40" wide)
    Dim stud_type As Integer 'Stud types: 1 = 2x4,  2 = LVL
    Dim clamp_size As Integer 'Clamp sizes: 1 = 8"-24",  2 = 12"-36",  3 = 24"-48"
    Dim brace_size As Integer 'Brace sizes: 1 = 7'-11',  2 = 11'-19'
    Dim col_wt As Integer
    Dim ply_name As String
    Dim stud_name As String
    Dim stud_name_full As String 'A more elaborate name to include LVL dimensions
    Dim stud_block As String
    Dim stud_block_spax As String
    Dim stud_block_bolt As String
    Dim stud_face_block As String
    Dim SQ_NAME As String
    Dim SQ_NAME_SLINGS As String
    Dim window As Boolean       'True = a window is used (x or y), False = no windows are used
    Dim WinX As Boolean
    Dim WinY As Boolean
    Dim WinPos As Double        'Distance from bottom of column to window seam
    Dim WinGap As Double        'Distance window is visually broken open by
    Dim WinStudOff As Double    'Distance studs are held back from plywood at window seam
    
    'Get/define basic window information
    WinX = chkWinX.Value
    WinY = chkWinY.Value
    If WinX = True Or WinY = True Then window = True
    WinPos = ConvertToNum(WinDim2.Value)    'Distance from bottom of column to window seam
    WinGap = 6                              'Distance window is visually broken open by
    WinStudOff = 1                          'Distance studs are held back from plywood at window seam
    
    'Define matricies for data inputs
    Dim stud_matrix() As Integer 'Number of studs vs width and height of column side
    
    'Other definitions
    Dim ply_thk As Double: ply_thk = 0.75
    Dim chamf_thk As Double: chamf_thk = 0.75
    Dim min_stud_gap As Double: min_stud_gap = 2.125 'Minimum distance required to fit a column brace assembly between studs
    Dim max_wt_single_top As Integer: max_wt_single_top = 2000 'Maximum weight where only one top clamp (use of flathead bolts) is needed
    Dim stud_base_gap As Double: stud_base_gap = 0.25 'Gap between bottom of stud and ground
    Dim bot_clamp_gap As Double: bot_clamp_gap = 8 'space between the bottom clamp and the ground.
    Dim stud_start_offset As Double: stud_start_offset = 0.125 'distance from outside of chamfer to face of first stud
    pi = 4 * Atn(1)
    
    'Assign input box values to variables
    x = ConvertToNum(ColumnCreator.WidthBox)
    y = ConvertToNum(ColumnCreator.LengthBox)
    z = ConvertToNum(ColumnCreator.HeightBox)
    n_col = ConvertToNum(ColumnCreator.QuantityBox)
    ply_name = ColumnCreator.PlyNameBox
    
    'Swap x and y values if a window is defined on the x side. Do this to be consistent in which clamp segment is swung out for the window.
    If WinX = True Then
        x = ConvertToNum(ColumnCreator.LengthBox)
        y = ConvertToNum(ColumnCreator.WidthBox)
        WinX = False
        WinY = True
    End If
    
    'Get stud type from button inputs (1 is 2x4, 2 is LVL)
    If Round(z, 3) <= 16 * 12 Then
        stud_type = 1
        stud_name = "2X4"
        stud_name_full = "2X4"
        stud_block = "VBA_2X4": stud_block_spax = "VBA_2X4_SPAX": stud_block_bolt = "VBA_2X4_BOLT"
        stud_face_block = "VBA_2X4_FACE"
    ElseIf Round(z, 3) > 16 * 12 Then
        stud_type = 2
        stud_name = "LVL"
        stud_name_full = "1.5"" X 3.5"" LVL"
        stud_block = "VBA_LVL": stud_block_spax = "VBA_LVL_SPAX": stud_block_bolt = "VBA_LVL_BOLT"
        stud_face_block = "VBA_LVL_FACE"
    Else
        MsgBox ("Error: Invalid stud type.")
    End If
    
    If window = True Then
        stud_block_spax_hidden = stud_block_spax & "_HIDDEN"
        stud_block_bolt_hidden = stud_block_bolt & "_HIDDEN"
    End If

    'Assign x and y values to array
    Dim Arr(2) As Double: Arr(0) = x: Arr(1) = y

    'Warn user if pour window is too large
    If window = True And Round(z - WinPos, 3) > 48 Then
        If MsgBox("Warning:" & vbNewLine & "Pour window exceeds 48"" in height. This is allowed but not recommended.", vbOKCancel + vbExclamation, "Warning") = vbCancel Then
            ColumnCreator.show
            Exit Sub
        End If
    End If
    
    'Check if user is trying to use a pour window and a picking loop
    If window = True And SquaringCornerOptionPickingButton.Value = True Then
        If MsgBox("Warning:" & vbNewLine & "You specified a picking loop instead of a regular squaring corner to be used and you have a pour window. The picking loop will be removed from 1 corner to allow the gates clamp to swing open.", vbOKCancel + vbExclamation, "Warning") = vbCancel Then
            ColumnCreator.show
            Exit Sub
        End If
    End If
    
    'Check if user is trying to make a column with a side < 14" with pickup loops
    If SquaringCornerOptionPickingButton.Value = True And (Round(x, 3) < 14 Or Round(y, 3) < 14) Then
        MsgBox ("Error:" & vbNewLine & "Columns with a side <14'' use regular squaring corners rotated 180 degrees. Picking loop squaring corners cannot be rotated 180 degrees.")
        ColumnCreator.show
        Exit Sub
    End If
    
    'Check if x or y is not a multiple of 2 inches (Gates clamp holes are 2" O.C.). Just give a warning if it isn't.
    If Round(Int(x) - x, 3) <> 0 Or Round(Int(y) - y, 3) <> 0 Then
        If MsgBox("Warning:" & vbNewLine & "Column plan dimensions are not divisible by 1 inch. Gates clamps have holes spaced 1 inch on center." & vbNewLine & vbNewLine & "Do you know what you're doing?", vbYesNo + vbExclamation, "Warning") = vbNo Then
            ColumnCreator.show
            Exit Sub
        End If
    End If
    
    'Assign squaring corner names, use rotated (180 degrees) squaring corners for columns with either side <14"
    If Round(x, 3) < 14 Or Round(y, 3) < 14 Then
        SQ_NAME = "VBA_GATES_SQUARING_CORNER_INV"
        SQ_NAME_SLINGS = "VBA_GATES_SQUARING_CORNER_INV" 'Slings moved to between studs.
    Else
        SQ_NAME = "VBA_GATES_SQUARING_CORNER"
        SQ_NAME_SLINGS = "VBA_GATES_SQUARING_CORNER_SLINGS"
    End If
    
    'If library block is missing: load VBA_Block_Library .dwg file as a block to load all needed blocks, then delete that file block
    Dim BlockExists As Boolean
    BlockExists = False

    'Check if library was loaded:
    For Each entry In ActiveDocument.Blocks
        If entry.Name = "VBA_SHIBBOLETH" Then
            BlockExists = True
            Exit For
        End If
    Next
    
    Dim insertionPnt(0 To 2) As Double
    insertionPnt(0) = 0#: insertionPnt(1) = 0#: insertionPnt(2) = 0#
    FileToInsert = FileLocationPrefix & "VBA_Block_Library.dwg"
    If BlockExists = False Then
        Dim BlockDwg As AcadBlockReference
        Set BlockDwg = ThisDrawing.ModelSpace.InsertBlock(insertionPnt, FileToInsert, 1#, 1#, 1#, 0)
        BlockDwg.Delete
    End If



'#####################################################################################
'                                     S T U D S
'#####################################################################################
    'Compute number of studs required for each side
    Dim filepath As String
    Dim row_num As Integer: row_num = 0 'height
    Dim col_num_x As Integer: col_num_x = 0 'x
    Dim col_num_y As Integer: col_num_y = 0 'y
    Dim n_studs_total As Integer 'Total studs on all sides excluding window side
    
    filepath = FileLocationPrefix & "Columns\n_stud_matrix.csv" 'Change THIS file location if needed.
    stud_matrix = ImportMatrix(filepath)

    'Find row_num
    For i = 1 To UBound(stud_matrix, 1) 'Cycle through each row
        If stud_matrix(i, 0) >= Round(z, 3) Then 'Look at first entry of each row and compare to column height (z). Round z to avoid floating point imprecision.
            row_num = i 'If value equals or exceds column height then that's the row we want.
            Exit For
        End If
    Next i
    
    'Find col_num, first check for exact match
    For i = 1 To UBound(stud_matrix, 2) 'x axis
        If stud_matrix(0, i) = Round(x, 3) Then
            col_num_x = i: Exit For
        End If
    Next i
    For i = 1 To UBound(stud_matrix, 2) 'y axis
        If stud_matrix(0, i) = Round(y, 3) Then
            col_num_y = i: Exit For
        End If
    Next i
    
    'Find col_num, second check for most conservative match. Wider columns do not always use more studs. Compare number of studs for the 2 nearest values and pick the highest
    If col_num_x = 0 Then
        For i = 1 To UBound(stud_matrix, 2)
            If stud_matrix(0, i) > Round(x, 3) Then
                If stud_matrix(row_num, i) >= stud_matrix(row_num, i - 1) Then
                    col_num_x = i:      Exit For
                Else
                    col_num_x = i - 1:  Exit For
                End If
            End If
        Next i
    End If
    If col_num_y = 0 Then
        For i = 1 To UBound(stud_matrix, 2)
            If stud_matrix(0, i) > Round(y, 3) Then
                If stud_matrix(row_num, i) >= stud_matrix(row_num, i - 1) Then
                    col_num_y = i:      Exit For
                Else
                    col_num_y = i - 1:  Exit For
                End If
            End If
        Next i
    End If
    
    n_studs_x = stud_matrix(row_num, col_num_x)
    n_studs_y = stud_matrix(row_num, col_num_y)
    n_studs_total = n_studs_x * 2 + n_studs_y * 2
    
    'MOVING STUDS FOR BRACE CLAMPS
    'Determine if studs must be moved to fit brace clamp
    Dim avg_gap_x As Double
    Dim avg_gap_y As Double
    Dim push_studs_x As Integer: push_studs_x = 0 'Variable to toggle whether studs should be moved to accomodate a brace clamp, default off
    Dim push_studs_y As Integer: push_studs_y = 0
    
    'Check if x side studs are too close
    avg_gap_x = (x + ply_thk - stud_start_offset - n_studs_x * 3.5) / (n_studs_x - 1) 'Finds gap between studs if they're evenly spaced
    If Round(avg_gap_x, 3) < Round(min_stud_gap, 3) Then 'If studs are evenly spaced and the gap between them is too small, toggle push studs on.
        push_studs_x = 1
    End If
    
    'Check if y side studs are too close
    avg_gap_y = (y + ply_thk - stud_start_offset - n_studs_y * 3.5) / (n_studs_y - 1)
    If Round(avg_gap_y, 3) < Round(min_stud_gap, 3) Then
        push_studs_y = 1
    End If
    
    'Compute stud spacing assuming equal spacing
    Dim stud_spacing_x() As Double
    Dim stud_spacing_y() As Double
    ReDim stud_spacing_x(1 To n_studs_x)
    ReDim stud_spacing_y(1 To n_studs_y)
    Dim available_2x2_x As Double 'Available length between studs for 2x2 inserts for window locks. Doesn't include where AFBs are located
    Dim available_2x2_y As Double
    Dim min_2x2_gap As Double:  min_2x2_gap = 1.625 'Minimum clearance between studs needed for a 1.5" 2x2 with 1/8" tolerance
    Dim AFB_x2 As Integer '1 if a 2nd AFB is inserted between studs on the x side (0 if only 1 AFB is inserted on x side)
    
    For i = 1 To n_studs_x
        stud_spacing_x(i) = stud_start_offset + (i - 1) * (3.5 + avg_gap_x)
    Next i
    For i = 1 To n_studs_y
        stud_spacing_y(i) = stud_start_offset + (i - 1) * (3.5 + avg_gap_y)
    Next i
    
    'The 3 clamp locations are: (1) near stud on longest side
    '                           (2) far stud OR clamp tail on longest side
    '                           (3) near stud on short side
    'The near stud is the left-most on the 'southern' clamp or the lower-most on the 'eastern' clamp
    'The near stud will always accommodate a brace clamp
    'The far stud will accommodate a brace clamp if there is room
    
    'If adjusting studs, first adjust them to make room for the AFB points
    If push_studs_x = 1 Then
        If avg_gap_x * (n_studs_x - 1) >= 2 * min_stud_gap Then
            stud_spacing_x(2) = stud_start_offset + 3.5 + min_stud_gap
            stud_spacing_x(UBound(stud_spacing_x) - 1) = stud_spacing_x(UBound(stud_spacing_x)) - 3.5 - min_stud_gap
            AFB_x2 = 1
        Else
            stud_spacing_x(UBound(stud_spacing_x) - 1) = stud_spacing_x(UBound(stud_spacing_x)) - 3.5 - min_stud_gap
            AFB_x2 = 0
        End If
    End If
    
    If push_studs_y = 1 Then
        If avg_gap_y * (n_studs_y - 1) >= 2 * min_stud_gap Then
            stud_spacing_y(2) = stud_start_offset + 3.5 + min_stud_gap
            stud_spacing_y(UBound(stud_spacing_y) - 1) = stud_spacing_y(UBound(stud_spacing_y)) - 3.5 - min_stud_gap
        Else
            stud_spacing_y(UBound(stud_spacing_y) - 1) = stud_spacing_y(UBound(stud_spacing_y)) - 3.5 - min_stud_gap
        End If
    End If
    
    'Check if any studs now overlap, if so, move the stud that's closer to the chamfer away
    For i = 1 To n_studs_x - 1
        If Round(stud_spacing_x(i + 1) - stud_spacing_x(i), 3) < 3.5 Then
            stud_spacing_x(i) = stud_spacing_x(i + 1) - 3.5
        End If
    Next i
    For i = 1 To n_studs_y - 1
        If Round(stud_spacing_y(i + 1) - stud_spacing_y(i), 3) < 3.5 Then
            stud_spacing_y(i) = stud_spacing_y(i + 1) - 3.5
        End If
    Next i
 
'    'For windows, try to optimize stud spacing to allow the maximum number of 2x2 window locks to be inserted
'    If window = True Then
'        'Start by getting clamp L (normally this would be found later in the clamps section)
'        If ClampSizeButton1.Value = True Then
'            clamp_L = 36
'        ElseIf ClampSizeButton2.Value = True Then
'            clamp_L = 48
'        ElseIf ClampSizeButton3.Value = True Then
'            clamp_L = 60
'        ElseIf ClampSizeButton4.Value = True Then
'            If Round(FindMax(Arr), 3) < 24 Then
'                clamp_L = 36
'            ElseIf Round(FindMax(Arr), 3) <= 36 Then
'                clamp_L = 48
'            ElseIf Round(FindMax(Arr), 3) <= 48 Then
'                clamp_L = 60
'            Else
'                MsgBox ("Error: Column is too wide (>48"""") in one dimension")
'            End If
'        End If
'
'        'Change AFB_x2 to 0 if AFB is on clamp away from studs
'        If clamp_L - 12.5 - x >= 8.5 Then
'            AFB_x2 = 0
'        End If
'
'        'Find total length of gaps minus gaps occupied by AFBs
'        available_2x2_x = avg_gap_x * (n_studs_x - 1) - (stud_spacing_x(UBound(stud_spacing_x)) - stud_spacing_x(UBound(stud_spacing_x) - 1) - 3.5) - AFB_x2 * (stud_spacing_x(2) - stud_spacing_x(1) - 3.5)
'        available_2x2_y = avg_gap_y * (n_studs_y - 1) - (stud_spacing_y(UBound(stud_spacing_y)) - stud_spacing_y(UBound(stud_spacing_y) - 1) - 3.5)
'
'        'x side
'        If available_2x2_x / (n_studs_x - 2 - AFB_x2) < min_2x2_gap Then
'            'Check if there's no room for any 2x2
'            If Round(available_2x2_x, 3) < Round(min_2x2_gap, 3) Then
'                GoTo Skip2x2X
'            Else
'                If n_studs_x = 4 Then
'                    'stud_spacing_x(UBound(stud_spacing_x) - 2) = stud_spacing_x(UBound(stud_spacing_x) - 1) - 3.5
'                ElseIf n_studs_x >= 5 Then
'                    'stud_spacing_x(UBound(stud_spacing_x) - 2) = stud_spacing_x(UBound(stud_spacing_x) - 1) - 3.5
'                    For i = 2 To UBound(stud_spacing_x) - 3
'
'                    Next i
'                End If
'            End If
'        End If
'Skip2x2X:
'        'y side
'        If available_2x2_y / (n_studs_x - 2) < min_2x2_gap Then
'            'Check if there's no room for any 2x2
'            If Round(available_2x2_y, 3) < Round(min_2x2_gap, 3) Then
'                GoTo Skip2x2Y
'            Else
'                If n_studs_y >= 5 Then
'                    'stud_spacing_y(UBound(stud_spacing_y) - 2) = stud_spacing_y(UBound(stud_spacing_y) - 1) - 3.5
'                    For i = 2 To n_studs_y - 3
'                        'stud_spacing_y(i) = stud_spacing_y(1) + 3.5 + (i - 2) * 3.5 + (i - 1) * available_2x2_y / (n_studs_y - 3)
'                    Next i
'                End If
'            End If
'        End If
'Skip2x2Y:
'    End If
    
    'Check again for overlap, this time only create a message if an issue is found, don't move the studs anymore.
    For i = 1 To n_studs_x - 1
        If Round(stud_spacing_x(i + 1) - stud_spacing_x(i), 3) < 3.5 Then
            MsgBox ("Error: Studs overlap, check and manually correct drawing.")
            GoTo EndOfStudChecks
        End If
    Next i
    For i = 1 To n_studs_y - 1
        If Round(stud_spacing_y(i + 1) - stud_spacing_y(i), 3) < 3.5 Then
            MsgBox ("Error: Studs overlap, check and manually correct drawing.")
            GoTo EndOfStudChecks
        End If
    Next i
    
    'Check whether studs have 1.5" clear between each for a pour window
    If window = True Then
        For i = 1 To n_studs_x - 1
            If Round(stud_spacing_x(i + 1) - stud_spacing_x(i), 3) < 5 Then
                'MsgBox ("Warning: Insufficient clearance between studs for a 2x2 window lock. Check and manually correct drawing if necessary.")
                GoTo EndOfStudChecks
            End If
        Next i
        For i = 1 To n_studs_y - 1
            If Round(stud_spacing_y(i + 1) - stud_spacing_y(i), 3) < 5 Then
                'MsgBox ("Warning: Insufficient clearance between studs for a 2x2 window lock. Check and manually correct drawing if necessary.")
                GoTo EndOfStudChecks
            End If
        Next i
    End If
    
EndOfStudChecks:
    

    
    
'#####################################################################################
'                                   P L Y W O O D
'#####################################################################################


    Dim ply_width_x As Double
    Dim ply_width_y As Double
    Dim ply_bot_n As Integer 'Number of 8'-0" by x'-x" sheets on the bottom of the column
    Dim ply_top_ht_min As Double: ply_top_ht_min = 6 'Smallest allowable strip of plywood at top of column
    Dim max_ply_ht As Double
    Dim ply_seams() As Double '1 dimensional matrix that stores vertical length of each ply piece. First entry is bottom plywood.
    Dim ply_seams_win() As Double '1 dimensional matrix that stores vertical length of each ply piece for the window panel (if any). First entry is bottom plywood.
    
    'Read plywood seams from the userform
    ply_seams = ReadSizes(ColumnCreator.boxPlySeams.Value)
    ply_seams_win = ReadSizes(ColumnCreator.boxPlySeams.Value) 'Assume ply_seams and ply_seams_win are the same, check for differences below
    
    'Re-validate the ply seams if somehow they have an issue
    If UpdatePly.ValidatePlySeams(ply_seams, x, y, z) = 0 Then
        MsgBox ("Error: Plywood layout invalid. You should never see this message...How did you do this?")
        GoTo last_line
    End If
    
    'Create ply_seams_win
    Dim temp_1 As Double: temp_1 = 0
    
    For i = 1 To UBound(ply_seams)
        temp_1 = temp_1 + ply_seams(i)
        'If the window seam aligns with a regular plywood seam, ply_seams and ply_seams_win are the same (already assigned)
        If Round(temp_1, 3) = Round(WinPos, 3) Then
            Exit For
        'If the window doesn't align, modify ply_seams_win to include the new seam
        ElseIf Round(temp_1, 3) > Round(WinPos, 3) Then
            ply_seams_win(i) = ply_seams_win(i) - (temp_1 - WinPos) 'Reduce the height of the cut plywood to the length below the window
            ReDim Preserve ply_seams_win(1 To UBound(ply_seams) + 1) 'Add 1 entry to the array
            ply_seams_win(i + 1) = ply_seams(i) - ply_seams_win(i) 'Add an entry for the plywood height remaining above the window
            If i < UBound(ply_seams) Then 'If there are more plywood pieces above the bisected one, add those back in too
                For j = i + 1 To UBound(ply_seams)
                    ply_seams_win(j + 1) = ply_seams(j)
                Next j
            End If
            Exit For
        End If
    Next i
    
    'Add 1.5 inches to nominal width for ply sheet width
    ply_width_x = x + 1.5
    ply_width_y = y + 1.5

        
    'Assign x or y information to the window panel and elevation view so it can easily be referenced
    Dim n_studs_w As Integer
    Dim ply_width_w As Double
    Dim stud_spacing_w() As Double
    Dim n_studs_e As Integer
    Dim ply_width_e As Double
    Dim stud_spacing_e() As Double
    
    If WinX = True Then 'WinX should never be true, it will always flip back to WinY = true
        n_studs_w = n_studs_x
        n_studs_e = n_studs_x
        ply_width_w = ply_width_x
        ply_width_e = ply_width_x
        ReDim stud_spacing_w(1 To UBound(stud_spacing_x))
        ReDim stud_spacing_e(1 To UBound(stud_spacing_x))
        For i = 1 To UBound(stud_spacing_x)
            stud_spacing_w(i) = stud_spacing_x(i)
            stud_spacing_e(i) = stud_spacing_x(i)
        Next i
    ElseIf WinY = True Then
        n_studs_w = n_studs_y
        n_studs_e = n_studs_y
        ply_width_w = ply_width_y
        ply_width_e = ply_width_y
        ReDim stud_spacing_w(1 To UBound(stud_spacing_y))
        ReDim stud_spacing_e(1 To UBound(stud_spacing_y))
        For i = 1 To UBound(stud_spacing_y)
            stud_spacing_w(i) = stud_spacing_y(i)
            stud_spacing_e(i) = stud_spacing_y(i)
        Next i
    Else 'If no window is used assume elevation view will display side x
        n_studs_e = n_studs_x
        ply_width_e = ply_width_x
        ReDim stud_spacing_e(1 To UBound(stud_spacing_x))
        For i = 1 To UBound(stud_spacing_x)
            stud_spacing_e(i) = stud_spacing_x(i)
        Next i
    End If
    
    'If column is very wide, use rotated sheets and thus 48" max height
    If Round(ply_width_x, 3) > 48 Or Round(ply_width_y, 3) > 48 Then
        max_ply_ht = 48
    Else
        max_ply_ht = 96
    End If

    'Check if window plywood would fit as one piece, if it does, change it
    If window = True Then
        Dim temp_2 As Double: temp_2 = 0
        Dim ply_cnt As Integer: ply_cnt = 0
        temp_1 = 0
        For i = 1 To UBound(ply_seams_win) - 1
            temp_1 = temp_1 + ply_seams_win(i)
            If Round(temp_1, 3) >= Round(WinPos, 3) Then
                ply_cnt = ply_cnt + 1
                temp_2 = temp_2 + ply_seams_win(i + 1)
            End If
        Next i
        If Round(temp_2, 3) <= Round(max_ply_ht, 3) Then
            ply_seams_win(UBound(ply_seams_win) - ply_cnt + 1) = temp_2
            ReDim Preserve ply_seams_win(1 To UBound(ply_seams_win) - ply_cnt + 1)
        End If
    End If
    
    'Count the number of maximally sized 4'-0" or 8'-0" plywood sheets used
    'Delete this?
    ply_bot_n = 0
    For i = 1 To UBound(ply_seams)
        If Round(ply_seams(i), 3) = Round(max_ply_ht, 3) Then
            ply_bot_n = ply_bot_n + 1
        End If
    Next i


    'Create 2D array for plywood cut counts. Columns: (width / height / quantity) 'ply_cuts(k, 1) = ply_width_x 'TRANSPOSE THIS STUPID MATRIX
    'First find number of unique sheet sizes
    Dim unique_plys As Integer
    Dim ply_widths(1 To 2) As Double
    Dim ply_cuts() As Double:   ReDim ply_cuts(1 To 3, 1 To 1) As Double    'Array for plywood sheet sizes for counts
    
    unique_plys = 0 '1 size of plywood is the bare minimum
    
    'Create array of plywood widths
    ply_widths(1) = ply_width_x
    ply_widths(2) = ply_width_y

    'For each entry in ply_seams
    For i = 1 To UBound(ply_seams)
        'For each side of the panel (A and B)
        For j = 1 To UBound(ply_widths)
            'Check if this width and height combination has been entered before, then add it to the existing entry or create an new entry
            For k = 1 To UBound(ply_cuts, 2)
                If Round(ply_cuts(1, k), 3) = Round(ply_widths(j), 3) And Round(ply_cuts(2, k), 3) = Round(ply_seams(i), 3) Then
                    ply_cuts(3, k) = ply_cuts(3, k) + 2 - Abs(WinX) * Abs(j = 1) - Abs(WinY) * Abs(j = 2) 'If this side is the same width as the window side, only add 1
                    GoTo ExitPlywoodCheckLoop
                ElseIf k = UBound(ply_cuts, 2) Then
                    unique_plys = unique_plys + 1
                    ReDim Preserve ply_cuts(1 To 3, 1 To unique_plys)
                    ply_cuts(1, unique_plys) = ply_widths(j)
                    ply_cuts(2, unique_plys) = ply_seams(i)
                    ply_cuts(3, unique_plys) = ply_cuts(3, unique_plys) + 2 - Abs(WinX) * Abs(j = 1) - Abs(WinY) * Abs(j = 2) 'If this side is the same width as the window side, only add 1
                    GoTo ExitPlywoodCheckLoop
                End If
            Next k
ExitPlywoodCheckLoop:
        Next j
    Next i

    'Remove the last line if it's 0 (before adding in the window plywoo
    If Round(ply_cuts(1, UBound(ply_cuts, 2)), 3) = 0 Then
        ReDim Preserve ply_cuts(1 To 3, 1 To UBound(ply_cuts, 2) - 1)
        unique_plys = unique_plys - 1
    End If

    'Add the window side plywood
    If window = True Then
        For i = 1 To UBound(ply_seams_win)
            'Check if this width and height combination has been entered before, then add it to the existing entry or create an new entry
            For k = 1 To UBound(ply_cuts, 2)
                If Round(ply_cuts(1, k), 3) = Round(ply_width_w, 3) And Round(ply_cuts(2, k), 3) = Round(ply_seams_win(i), 3) Then
                    ply_cuts(3, k) = ply_cuts(3, k) + 1
                    GoTo ExitPlywoodCheckLoop2
                ElseIf k = UBound(ply_cuts, 2) Then
                    unique_plys = unique_plys + 1
                    ReDim Preserve ply_cuts(1 To 3, 1 To unique_plys)
                    ply_cuts(1, unique_plys) = ply_width_w
                    ply_cuts(2, unique_plys) = ply_seams_win(i)
                    ply_cuts(3, unique_plys) = ply_cuts(3, unique_plys) + 1
                    GoTo ExitPlywoodCheckLoop2
                End If
            Next k
ExitPlywoodCheckLoop2:
        Next i
    End If
    
    'Remove the last line if it's 0
    If Round(ply_cuts(1, UBound(ply_cuts, 2)), 3) = 0 Then
        ReDim Preserve ply_cuts(1 To 3, 1 To UBound(ply_cuts, 2) - 1)
        unique_plys = unique_plys - 1
    End If
    
'Dim msg As String
'    For i = 1 To UBound(ply_cuts, 2)
'        For ii = 1 To UBound(ply_cuts, 1)
'            msg = msg & ply_cuts(ii, i) & vbTab 'replace with space(1) if array too big
'        Next ii
'        msg = msg & vbCrLf
'    Next i
'MsgBox msg

    
'#####################################################################################
'                                   C L A M P S
'#####################################################################################
    'Compute clamp size. Use maximum dimension to pick clamp.
    '1 = 8"-24",  2 = 12"-36",  3 = 24"-48"
    Dim clamp_spacing() As Double
    Dim swing_ang As Double 'Opened clamp angle shown in plan view for display purposes
    Dim win_clamp_top_max As Double: win_clamp_top_max = 5 'Maximum distance clamp above window seam can be from the seam
    Dim win_clamp_bot_max As Double: win_clamp_bot_max = 4 'Maximum distance clamp below window seam can be from the seam
    
    If ClampSizeButton1.Value = True Then
        GoTo Clampsize1
    ElseIf ClampSizeButton2.Value = True Then
        GoTo Clampsize2
    ElseIf ClampSizeButton3.Value = True Then
        GoTo Clampsize3
    ElseIf ClampSizeButton4.Value = True Then
        GoTo ClampSizeChoose
    End If
    
    
    
ClampSizeChoose:
    If Round(FindMax(Arr), 3) < 24 Then
Clampsize1:
        clamp_size = 1
        clamp_L = 36
        clamp_name = "8/24"
        clamp_block_bk = "VBA_8-24_CLAMP_PLAN_BACK"
        clamp_block_op = "VBA_8-24_CLAMP_PLAN_OP"
        clamp_block_pr = "VBA_8-24_CLAMP_PROFILE"
    ElseIf Round(FindMax(Arr), 3) <= 36 Then
Clampsize2:
        clamp_size = 2
        clamp_L = 48
        clamp_name = "12/36"
        clamp_block_bk = "VBA_12-36_CLAMP_PLAN_BACK"
        clamp_block_op = "VBA_12-36_CLAMP_PLAN_OP"
        clamp_block_pr = "VBA_12-36_CLAMP_PROFILE"
    ElseIf Round(FindMax(Arr), 3) <= 48 Then
Clampsize3:
        clamp_size = 3
        clamp_L = 60
        clamp_name = "24/48"
        clamp_block_bk = "VBA_24-48_CLAMP_PLAN_BACK"
        clamp_block_op = "VBA_24-48_CLAMP_PLAN_OP"
        clamp_block_pr = "VBA_24-48_CLAMP_PROFILE"
    Else
        MsgBox ("Error: Column is too wide (>48"""") in one dimension")
    End If
    
    'Convert clamp block names to window specific blocks if needed
    If window = True Then
        If WinY = True Then
            clamp_block_pr = clamp_block_pr & "_FLIPPED"
        End If
        clamp_block_op = clamp_block_op & "_WIN"
        swing_ang = -pi / 4
    End If
    
    'Determine clamp spacing
    filepath = FileLocationPrefix & "Columns\clamp_matrix.csv"
    clamp_matrix = ImportMatrix(filepath)
    
    'Find row number corresponding to longer side of column
    If x <= y Then
        long_side = y
    Else
        long_side = x
    End If
    
    For i = 0 To UBound(clamp_matrix, 1) 'Cycle through each row
        If clamp_matrix(i, 0) >= Round(long_side, 3) Then 'Look at first entry of each row and compare to the width of the long side.
            row_num = i 'If value equals or exceds that width then that's the row we want.
            Exit For
        End If
    Next i

    'Build clamp spacing matrix
    ReDim clamp_spacing(1 To UBound(clamp_matrix, 2))
    k = 0
    
    For i = 1 To UBound(clamp_matrix, 2) 'First column (index 0) is column sizes, clamp spacings start on 2nd column (index 1)
        If clamp_matrix(row_num, i) = 0 Then 'Store all non-zero values. When a 0 is encountered, exit the loop and redim to truncate off the trailing 0s
            ReDim Preserve clamp_spacing(1 To k)
            Exit For
        Else
            clamp_spacing(i) = clamp_matrix(row_num, i)
            k = k + 1
        End If
    Next i
    
    'Reduce clamp_spacing to fit actual column size. Use number of clamps for the larger size (a 9'-8" column uses clamps designed for a 10'-0" column)
    'First cut off all clamps below actual height
    ht_rem = z - bot_clamp_gap
    
    For i = 1 To UBound(clamp_spacing) - 1 'Look at the length of column above the bottom clamp
        If Round(clamp_spacing(i), 3) <= Round(ht_rem, 3) Then 'Starting at the top, subtract clamp spacings until the clamp spacing is larger than whatever distance remains
            n_clamps = n_clamps + 1
            ht_rem = ht_rem - clamp_spacing(i)
        Else
            n_clamps = n_clamps + 1 'When the clamp no longer fits add back the bottom clamp to the count and exit the loop
            Exit For
        End If
    Next i

    'Cut off all clamps below what fits onto this column and add back the bottom spacing
    ReDim Preserve clamp_spacing(1 To n_clamps + 1)
    clamp_spacing(UBound(clamp_spacing)) = bot_clamp_gap
    
    'Sum all clamp spacings from truncated matrix
    tot_temp = 0
    For i = 1 To UBound(clamp_spacing)
        tot_temp = tot_temp + clamp_spacing(i)
    Next i
    
    'Reduce spacing of 2nd from bottom clamp so sum of clamp spacings = z
    clamp_spacing(UBound(clamp_spacing) - 1) = clamp_spacing(UBound(clamp_spacing) - 1) - (tot_temp - z)
    
    'Cycle through all clamp spacings and check that they're >= 8". If less, move lowest non-compliant clamp to 8" and adjust the clamp above it accordingly, repeat until all clamps pass
    Dim infExit As Integer: infExit = 0
TestClampSpacing:
    For i = 1 To UBound(clamp_spacing)
        If Round(clamp_spacing(i), 3) < 8 Then
            clamp_spacing(i - 1) = clamp_spacing(i - 1) - (8 - clamp_spacing(i))
            clamp_spacing(i) = 8
            infExit = infExit + 1
            If infExit > 100 Then
                MsgBox ("Error: Infinite loop encountered while computing clamp spacings.")
                Exit For
            Else
                GoTo TestClampSpacing
            End If
        End If
    Next i

    'Make array of clamp locations by continuous dimensions
    Dim clamp_spacing_con()
    ReDim clamp_spacing_con(1 To UBound(clamp_spacing))
    clamp_spacing_con(1) = z - clamp_spacing(1)
    For i = 2 To UBound(clamp_spacing)
        clamp_spacing_con(i) = clamp_spacing_con(i - 1) - clamp_spacing(i)
    Next i
    
    'Modify clamp spacing for a window, if any
    Dim temp_value As Double 'Used to hold data during sorting algorithm
    
    If window = True Then
        'If lower clamp is too far from seam, add a lower clamp near the seam
        For i = 1 To UBound(clamp_spacing_con) - 1 'Last value is always 0, and not a clamp
            If Round(clamp_spacing_con(i), 3) <= Round(WinPos, 3) Then
                If Round(WinPos, 3) - Round(clamp_spacing_con(i), 3) > Round(win_clamp_bot_max, 3) Then
                    'If the lower clamp is further than the limit
                    n_clamps = n_clamps + 1
                    ReDim Preserve clamp_spacing_con(1 To n_clamps + 1)
                    For j = i To n_clamps - 1
                        clamp_spacing_con(n_clamps - j + i) = clamp_spacing_con(n_clamps - j + i - 1)
                    Next j
                    clamp_spacing_con(i) = WinPos - win_clamp_bot_max
                    clamp_spacing_con(UBound(clamp_spacing_con)) = 0

                    'If the added clamp is too close (<8") to the one below it, move the one below it
                    If Round(clamp_spacing_con(i + 1) - clamp_spacing_con(i), 3) < 8 Then
                        clamp_spacing_con(i + 1) = Int((clamp_spacing_con(i + 2) + clamp_spacing_con(i)) / 2)
                    End If
                    
                    GoTo LowerWinClampSet
                ElseIf Round(WinPos - clamp_spacing_con(i), 3) <= Round(win_clamp_bot_max, 3) Then
                    'If the lower clamp is within the limit, just move the lower clamp a bit lower. Clamp spacing should be too great for this to ever possibly conflict with another clamp
                    clamp_spacing_con(i) = WinPos - win_clamp_bot_max
                    GoTo LowerWinClampSet
                End If
            End If
        Next i
LowerWinClampSet:

        'If upper clamp is too far from seam, add an upper clamp near the seam
        Dim io As Integer
        For i = 1 To UBound(clamp_spacing_con) - 1 'Last value is always 0, and not a clamp
            io = UBound(clamp_spacing_con) - i 'Actual index of clamp (ordered from top to bottom)
            If Round(clamp_spacing_con(io), 3) > Round(WinPos, 3) Then
                If Round(clamp_spacing_con(io), 3) - Round(WinPos, 3) > Round(win_clamp_top_max, 3) Then
                    'If the upper clamp is further than the limit
                    'MsgBox i
                    
                    n_clamps = n_clamps + 1
                    ReDim Preserve clamp_spacing_con(1 To n_clamps + 1)
                    clamp_spacing_con(UBound(clamp_spacing_con)) = WinPos + win_clamp_top_max
                    'Sort spacing from largest to smallest (bubble sort algorithm)
                    'ReDim Preserve sorted_clamp_spacing_con(1 To UBound(clamp_spacing_con))
                    For j = 1 To UBound(clamp_spacing_con) - 1
                        For k = 1 To UBound(clamp_spacing_con) - j
                            If clamp_spacing_con(k + 1) > clamp_spacing_con(k) Then 'If next value is higher than current value, swap those values
                                temp_value = clamp_spacing_con(k)
                                clamp_spacing_con(k) = clamp_spacing_con(k + 1)
                                clamp_spacing_con(k + 1) = temp_value
                            End If
                        Next k
                    Next j
   
                    'If the added clamp is too close (<8") to the one above it, move the one above it
                    If Round(clamp_spacing_con(io) - clamp_spacing_con(io + 1), 3) < 8 Then
                        If io >= 2 Then
                            clamp_spacing_con(io) = Int((clamp_spacing_con(io - 1) + clamp_spacing_con(io + 1)) / 2)
                        Else 'Case when moving top clamp up
                            clamp_spacing_con(io) = clamp_spacing_con(io + 1) + 8
                        End If
                    End If
                    
                    GoTo UpperWinClampSet
                ElseIf Round(clamp_spacing_con(io) - WinPos, 3) <= Round(win_clamp_top_max, 3) And Round(clamp_spacing_con(io) - WinPos, 3) >= 0 Then
                    'If the upper clamp is within the limit, just move the upper clamp a bit higher. Clamp spacing should be too great for this to ever possibly conflict with another clamp
                    clamp_spacing_con(io) = WinPos + win_clamp_top_max
                    GoTo UpperWinClampSet
                End If
            End If
        Next i
UpperWinClampSet:
                 
        'Redefine the clamp_spacing array
        ReDim clamp_spacing(1 To n_clamps + 1)
        
        clamp_spacing(1) = z - clamp_spacing_con(1)
        For i = 2 To n_clamps
            clamp_spacing(i) = clamp_spacing_con(i - 1) - clamp_spacing_con(i)
        Next i
        clamp_spacing(n_clamps + 1) = clamp_spacing_con(UBound(clamp_spacing_con) - 1)
    End If
    
    n_reinf_angles = 0
    
    'Count reinforcing angles on x side
    If x > 40 Then
        For i = 1 To UBound(clamp_spacing_con) - 1 'Last value is a 0
            If (z - clamp_spacing_con(i)) >= 87 Then
                n_reinf_angles = n_reinf_angles + 1
            End If
        Next i
    End If
    
    'Count reinforcing angles on y side
    If y > 40 Then
        For i = 1 To UBound(clamp_spacing_con) - 1 'Last value is a 0
            If (z - clamp_spacing_con(i)) >= 87 Then
                n_reinf_angles = n_reinf_angles + 1
            End If
        Next i
    End If
    
    n_reinf_angles = n_reinf_angles * 2
        
    'Warn user if only 1 clamp is on pour window
    If window = True Then
        If clamp_spacing_con(2) < WinPos Then
            If MsgBox("Warning:" & vbNewLine & "Pour window is only secured by 1 clamp. Consult with an engineering manager. Press OK to continue.", vbOKCancel + vbExclamation, "Warning") = vbCancel Then
                ColumnCreator.show
                Exit Sub
            End If
        End If
    End If
'#####################################################################################
'                           M I S C E L L A N E O U S
'#####################################################################################
    
    Dim n_bolts As Integer
    Dim n_screws As Integer
    Dim n_chamf As Integer
    Dim chamf_length As Integer: chamf_length = 12 '12ft chamfer length is assumed

    'Compute brace size
    If z < 160 Then
        brace_size = 1
        brace_L_stored = 79.6
        brace_name = "7'-TO-11'"
        brace_block = "VBA_AFB_7-11"
    Else
        brace_size = 2
        brace_L_stored = 128.6
        brace_name = "11'-TO-19'"
        brace_block = "VBA_AFB_11-19"
    End If
    
    'Find which clamp gets braced (aim for nearest to 70% of column height)
    i = 1
    Do While clamp_spacing_con(i) > z * 0.7
        i = i + 1
    Loop
    If Abs(clamp_spacing_con(i) - z * 0.7) < Abs(clamp_spacing_con(i - 1) - z * 0.7) Then 'If lower clamp is closer, assign that one, else the other
        brace_clamp = i
    Else
        brace_clamp = i - 1
    End If
    
    'If brace goes below 4" above base of column when packed, move it up a clamp and test again
    Do While clamp_spacing_con(brace_clamp) + 0.9289 < brace_L_stored + 4
        brace_clamp = brace_clamp - 1
    Loop
    
    'Find which clamp gets the chain to secure the brace
    chain_clamp = 1 ' initialize
    Do While clamp_spacing_con(chain_clamp) > clamp_spacing_con(brace_clamp) + 0.9289 - brace_L_stored + 1 'Terminates after chain clamp is just below brace
        chain_clamp = chain_clamp + 1
    Loop
    chain_clamp = chain_clamp - 1
    
    'Call module to calculate total weight
    col_wt = wt_total(x, y, z, n_studs_x, n_studs_y, stud_type, n_clamps, clamp_size, brace_size)

    'Determine number of "top clamps" are required based on column weight
    If col_wt <= max_wt_single_top Then
        n_top_clamps = 1
    Else
        n_top_clamps = 2
    End If
    
    'Count fasteners
    n_bolts = (n_studs_total * n_top_clamps) + (2 * (n_clamps - n_top_clamps))
    n_screws = (n_studs_total - 2) * (n_clamps - n_top_clamps)
    
    'Compute number of chamfer pieces
    If z = 144 Then
        n_chamf = 4
    Else
        n_chamf = 4 * RoundDown((z / 12) / chamf_length) + RoundUp(4 / (12 / (z / 12 - chamf_length * RoundDown((z / 12) / chamf_length)))) 'when
        If z <= chamf_length * 12 Then                                               '[    this term becomes 0 when z <= chamf_length      ]
            n_chamf = 4
        End If
    End If
    
'#####################################################################################
'                                     T E X T
'#####################################################################################
    
    'Insert material count text
    Dim MTextObject1 As AcadMText
    Dim MTextObject2 As AcadMText
    Dim objTextStyle As AcadTextStyle
    Dim pt_click() As Double
    Dim qty_text As String
    Dim pt_o(0 To 2) As Double 'lower left corner of sheet border
    Dim pt1(0 To 2) As Double  'Fabrication notes
    Dim pt2(0 To 2) As Double  'Title text for fabrication notes and quantities
    Dim pt3(0 To 2) As Double  'Quantity/components text
    
    ThisDrawing.ActiveSpace = acModelSpace
    pt_click = ThisDrawing.Utility.GetPoint(, "Click to place")
    
    pt_o(0) = pt_click(0) + 20.23568507: pt_o(1) = pt_click(1) + 5.17943146: pt_o(2) = 0
    pt1(0) = pt_o(0) + 448.4: pt1(1) = pt_o(1) + 360
    pt2(0) = pt1(0) + 0: pt2(1) = pt1(1) + 7
    pt3(0) = pt1(0) + 0: pt3(1) = pt1(1) - 52
    
    'FABRICATION NOTES AND QUANTITIES
    ThisDrawing.ActiveLayer = ThisDrawing.Layers("FORM")
    
    Set MTextObject1 = ThisDrawing.ModelSpace.AddMText(pt1, 100, _
    "• COLUMN SIZE = " & x & "'' X " & y & "''" & vbCrLf & vbCrLf & _
    "• NUMBER OF COLUMN FORMS = " & n_col & "-EA" & vbCrLf & vbCrLf & _
    "• COLUMN FORM WEIGHT (APPROXIMATE) = " & col_wt & "-LBS" & vbCrLf & vbCrLf & _
    "• PLYWOOD = 3/4'' PLYFORM (" & ply_name & "), CLASS-1 (MIN)" & vbCrLf & vbCrLf & _
    "• COLUMN FORMS AND CLAMP SPACING LAYOUTS FOR L4 X 3 X 1/4 GATES LOK-FAST COLUMN CLAMPS ARE DESIGNED FOR A POUR RATE = FULL LIQUID HEAD U.N.O." & vbCrLf & vbCrLf & _
    "• CONTACT THE MCC ENGINEER PRIOR TO ANY CHANGES OR MODIFICATIONS TO THE DETAILS ON THIS SHEET.")
    MTextObject1.StyleName = "Arial Narrow"
    MTextObject1.Height = 2
    
    'Plywood quantities
    For i = 1 To UBound(ply_cuts, 2)
        qty_text = qty_text & "• (" & ply_cuts(3, i) * n_col & "-EA) = (" & n_col & "-COL) X (" & ply_cuts(3, i) & "-EA/COL) @ " & ConvertFtIn(ply_cuts(1, i)) & " WIDE X " & ConvertFtIn(ply_cuts(2, i)) & " LONG 3/4'' PLYWOOD" & vbCrLf
    Next i
    qty_text = "PLYWOOD" & vbCrLf & qty_text & vbCrLf
    
    'Stud quantities
    If window = False Then
        qty_text = qty_text & "STUDS" & vbCrLf & "• (" & n_studs_total * n_col & "-EA) = (" & n_col & "-COL) X (" & n_studs_total & "-EA/COL) @ " & ConvertFtIn(z - 0.25) & " " & stud_name_full
    Else
        qty_text = qty_text & "STUDS" & vbCrLf & "• (" & (n_studs_total - n_studs_w) * n_col & "-EA) = (" & n_col & "-COL) X (" & (n_studs_total - n_studs_w) & "-EA/COL) @ " & ConvertFtIn(z - 0.25) & " " & stud_name_full & vbCrLf
        qty_text = qty_text & "• (" & n_studs_w * n_col & "-EA) = (" & n_col & "-COL) X (" & n_studs_w & "-EA/COL) @ " & ConvertFtIn(WinPos - WinStudOff - 0.25) & " " & stud_name_full & vbCrLf
        qty_text = qty_text & "• (" & n_studs_w * n_col & "-EA) = (" & n_col & "-COL) X (" & n_studs_w & "-EA/COL) @ " & ConvertFtIn(z - WinPos - WinStudOff) & " " & stud_name_full
    End If
    
    'Clamp quantities
    qty_text = qty_text & vbCrLf & vbCrLf & "COLUMN CLAMPS" & vbCrLf
    qty_text = qty_text & "• (" & n_clamps * n_col & "-EA) = (" & n_col & "-COL) X (" & n_clamps & "-EA/COL) @ GATES " & clamp_name & " LOK-FAST CLAMP ASSEMBLIES (SETS)."
    If n_reinf_angles > 0 Then
        qty_text = qty_text & vbCrLf & "• (" & n_reinf_angles * n_col & "-EA) = (" & n_col & "-COL) X (" & n_reinf_angles & "-EA/COL) @ GATES REINFORCING ANGLES"
    End If
    
    'Fastener quantities
    Dim n_nuts As Integer: n_nuts = 0 'Number of 1/2" coil rod nuts for threaded rods
    qty_text = qty_text & vbCrLf & vbCrLf & "FASTENERS" & vbCrLf & _
    "•   (" & n_bolts * n_col & "-EA) = (" & n_col & "-COL) X (" & n_bolts & "-EA/COL) @ 5/16'' X 3'' GATES FLAT HEAD BOLTS" & vbCrLf & _
    "•   (" & n_bolts * n_col & "-EA) = (" & n_col & "-COL) X (" & n_bolts & "-EA/COL) @ 5/16''-18 UNC NYLOK LOCK NUTS" & vbCrLf & _
    "•   (" & n_screws * n_col & "-EA) = (" & n_col & "-COL) X (" & n_screws & "-EA/COL) @ 1/4'' X 2-3/8'' GATES SPAX POWERLAG SCREWS" & vbCrLf
    
    '36" threaded rod if it occurs
    If n_top_clamps >= 2 Or SquaringCornerOptionPickingButton.Value = True Then
        qty_text = qty_text & _
        "•   (" & n_col * 2 & "-EA) = (" & n_col & "-COL) X (2-EA/COL) @ 1/2''-13 UNC X +/-36'' LONG ALL-THREADED ROD" & vbCrLf
        n_nuts = n_nuts + 8
    End If
    
    '14" threaded rod if it occurs (must have window, if there's a 36" rod only include a 14" rod if the 2nd top clamp is above the window, if there's no 36" rod always include a 14" rod)
    If (window = True And (n_top_clamps >= 2 Or SquaringCornerOptionPickingButton.Value = True) And clamp_spacing_con(2) > WinPos) Or (window = True And n_top_clamps < 2 And SquaringCornerOptionPickingButton.Value = False) Then
        qty_text = qty_text & _
        "•   (" & n_col & "-EA) = (" & n_col & "-COL) X (2-EA/COL) @ 1/2''-13 UNC X +/-14'' LONG ALL-THREADED ROD" & vbCrLf
        n_nuts = n_nuts + 4
    End If
    
    'Nuts and washers for threaded rods
    If n_nuts > 0 Then
        qty_text = qty_text & _
        "•   (" & n_nuts * n_col & "-EA) = (" & n_col & "-COL) X (" & n_nuts & "-EA/COL) @ 1/2''-13 UNC NYLOK LOCK NUTS" & vbCrLf & _
        "•   (" & n_nuts * n_col & "-EA) = (" & n_col & "-COL) X (" & n_nuts & "-EA/COL) @ 1/2'' STANDARD FLAT WASHER" & vbCrLf & vbCrLf
    End If
    
    'Chamfer quantity
    qty_text = qty_text & "3/4'' GATES PLASTIC CHAMFER (BASED ON 12' CHAMFER LENGTHS)" & vbCrLf & _
    "•   (" & n_col * n_chamf & "-EA) = (" & n_col & "-COL) X (" & n_chamf & "-EA/COL) @ " & chamf_length & "'-0'' LONG PIECES"
    
    'AFB quantity
    qty_text = qty_text & vbCrLf & vbCrLf & "GATES ADJUSTABLE FORM BRACES (INCLUDING FORM BASE PLATES)" & vbCrLf & _
    "•   (" & n_col * 3 & "-EA) = (" & n_col & "-COL) X (3EA/COL) " & brace_name & " LONG GATES AFB" & vbCrLf & vbCrLf
    
    'Hoisting slings
    If col_wt <= 2400 Then
        qty_text = qty_text & "HOISTING SLINGS" & vbCrLf & _
        "•   (" & n_col * 2 & "-EA) = (" & n_col & "-COL) X (2EA/COL) ENDLESS ROUND SLINGS; LIFTEX P/N ''ENR1'', PURPLE." & vbCrLf & "SWL = 2400-LBS. PER SLING IN CHOKER CONFIGURATION."
    Else
        qty_text = qty_text & "HOISTING SLINGS" & vbCrLf & _
        "•   (" & n_col * 2 & "-EA) = (" & n_col & "-COL) X (2EA/COL) ENDLESS ROUND SLINGS; LIFTEX P/N ''ENR2'', GREEN." & vbCrLf & "SWL = 4800-LBS. PER SLING IN CHOKER CONFIGURATION."
    End If
        
    'Set all count and fab note texts
    Set MTextObject1 = ThisDrawing.ModelSpace.AddMText(pt3, 100, qty_text)
    MTextObject1.Height = 2
    MTextObject1.StyleName = "Arial Narrow" 'Forces use of Arial Narrow text style
        
    '#####################################################################################
    '                                 D R A W I N G
    '#####################################################################################
    Dim BlockRefObj As AcadBlockReference 'Create block reference object
    Dim ObjDynBlockProp As AcadDynamicBlockReferenceProperty
    Dim LineObj As AcadLine
    Dim PlyTemp As Double
    Dim ptA(0 To 2) As Double 'lower left corner of side A elevation view plywood
    Dim ptB(0 To 2) As Double 'lower left corner of side B elevation view plywood
    Dim ptW(0 To 2) As Double 'lower left corner of side W (window) elevation view plywood
    Dim ptE(0 To 2) As Double 'Lower left corner of clamp elevation view (right side of ply edge)
    
    Dim pt4(0 To 2) As Double 'Plywood seam locations for sides A and B
    Dim pt5(0 To 2) As Double 'Stud locations on turned out clamp in plan view
    Dim pt6(0 To 2) As Double 'stud locations for sides A, B, and W
    Dim pt7(0 To 2) As Double 'UNUSED
    Dim pt8(0 To 2) As Double 'Elevation section ply base for side A
    Dim pt9(0 To 2) As Double 'Elevation section ply base for side B
    Dim pt10(0 To 2) As Double 'Elevation section ply base for side W
    Dim pt11(0 To 2) As Double 'stud locations at elevation section for sides A, B, and W
    Dim pt12(0 To 2) As Double 'ply+chamfer for plan view
    Dim pt13(0 To 2) As Double 'origin point on plan view
    Dim pt14(0 To 2) As Double 'stud locs for plan view
    Dim pt15(0 To 2) As Double 'clamp locs for plan view
    Dim pt16(0 To 2) As Double 'brace locs for plan view
    Dim pt17(0 To 2) As Double 'Text locs for plan view
    Dim pt18(0 To 2) As Double 'Chamfer locations for elevation views
    Dim pt20(0 To 2) As Double 'stud locations at base of clamp elevation and framing lumber at base
    Dim pt21(0 To 2) As Double 'Clamp locations in elevation
    Dim pt22(0 To 2) As Double 'Clamp dimensions in inches from bottom
    Dim pt23(0 To 2) As Double 'Start point for top clamp dim line
    Dim pt24(0 To 2) As Double 'End point for top clamp dim line
    Dim pt25(0 To 2) As Double '"CLAMP" and "TOP CLAMP" labels
    Dim pt26(0 To 2) As Double 'Lifting sling points
    Dim pt27(0 To 2) As Double 'Coil rod and nuts for top clamps
    Dim pt28(0 To 2) As Double 'Brace related locations
    Dim pt29(0 To 2) As Double 'Screw heads for ply elevations
    Dim pt30(0 To 2) As Double 'Misc. notes and details
    Dim pt31(0 To 2) As Double 'Reinforcing angles for wide columns
    Dim pt32(0 To 2) As Double 'Lower left text for column count
    Dim pt33(0 To 2) As Double 'A & B elevation sights for plan views
    Dim pt34(0 To 2) As Double 'Insertion point for timestamp (lower left corner, outside of sheet)
    Dim pt_blk(0 To 2) As Double
    
    'Control which elevation views are drawn and space them accordingly
    Dim DrawB As Boolean: DrawB = False     'Side B (if different)
    Dim DrawW As Boolean: DrawW = False     'Window panel, if any

    'Identical sides, no window (2 views)
    If Round(x, 3) = Round(y, 3) And window = False Then
        ptA(0) = pt_o(0) + 245: ptA(1) = pt_o(1) + 25
        ptE(0) = pt_o(0) + 100: ptE(1) = pt_o(1) + 25
    'Identical sides, with window (3 views)
    ElseIf Round(x, 3) = Round(y, 3) And window = True Then
        ptW(0) = pt_o(0) + 300: ptW(1) = pt_o(1) + 25
        ptA(0) = pt_o(0) + 185: ptA(1) = pt_o(1) + 25
        ptE(0) = pt_o(0) + 54.5: ptE(1) = pt_o(1) + 25
        DrawW = True
    'Different sides, no window (3 views)
    ElseIf Round(x, 3) <> Round(y, 3) And window = False Then
        ptA(0) = pt_o(0) + 300: ptA(1) = pt_o(1) + 25
        ptB(0) = pt_o(0) + 185: ptB(1) = pt_o(1) + 25
        ptE(0) = pt_o(0) + 54.5: ptE(1) = pt_o(1) + 25
        DrawB = True
    'Different sides, with window (4 views)
    ElseIf Round(x, 3) <> Round(y, 3) And window = True Then
        ptW(0) = pt_o(0) + 340 - 0.5 * ply_width_w: ptW(1) = pt_o(1) + 25
        ptA(0) = pt_o(0) + 267.25 - 0.5 * ply_width_x: ptA(1) = pt_o(1) + 25
        ptB(0) = pt_o(0) + 190 - 0.5 * ply_width_y: ptB(1) = pt_o(1) + 25
        ptE(0) = pt_o(0) + 54.5 - 0.5 * (ply_width_w - 24): ptE(1) = pt_o(1) + 25
        DrawB = True
        DrawW = True
    End If

    'ELEVATION VIEWS
    
    ThisDrawing.ActiveLayer = ThisDrawing.Layers("FORM")
    'Profile of B side studs
    Call DrawRectangle(ptE(0) - ply_thk, ptE(1) + stud_base_gap, ptE(0) - ply_thk - 1.5, ptE(1) + z)
    
    'Draw studs
        'Side A
        For i = 1 To n_studs_x
            pt6(0) = ptA(0) + ply_width_x + chamf_thk - 3.5 - stud_spacing_x(i)
            pt6(1) = ptA(1) + stud_base_gap
            Set BlockRefObj = ThisDrawing.ModelSpace.InsertBlock(pt6, stud_face_block, 1#, 1#, 1#, pi / 2) 'Insert studs
            Call ChangeProp(BlockRefObj, "Distance1", z - stud_base_gap)
        Next i
        
        'Side B
        If DrawB = True Then
            For i = 1 To n_studs_y
                pt6(0) = ptB(0) + ply_width_y + chamf_thk - 3.5 - stud_spacing_y(i)
                pt6(1) = ptB(1) + stud_base_gap
                Set BlockRefObj = ThisDrawing.ModelSpace.InsertBlock(pt6, stud_face_block, 1#, 1#, 1#, pi / 2) 'Insert studs
                Call ChangeProp(BlockRefObj, "Distance1", z - stud_base_gap)
            Next i
        End If
        
        'Side W
        If DrawW = True Then
            For i = 1 To n_studs_w
                pt6(0) = ptW(0) + ply_width_w + chamf_thk - 3.5 - stud_spacing_w(i): pt6(1) = ptW(1) + stud_base_gap
                Set BlockRefObj = ThisDrawing.ModelSpace.InsertBlock(pt6, stud_face_block, 1#, 1#, 1#, pi / 2) 'Insert studs below window
                Call ChangeProp(BlockRefObj, "Distance1", WinPos - WinStudOff - stud_base_gap)
                pt6(1) = ptW(1) + WinPos + WinStudOff + WinGap
                Set BlockRefObj = ThisDrawing.ModelSpace.InsertBlock(pt6, stud_face_block, 1#, 1#, 1#, pi / 2) 'Insert studs on window
                Call ChangeProp(BlockRefObj, "Distance1", z - WinPos - WinStudOff)
            Next i
        End If
        
    'Draw plywood sheets
    ThisDrawing.ActiveLayer = ThisDrawing.Layers("PLYA")
    pt4(1) = ptA(1)
    For i = 1 To UBound(ply_seams)
        pt4(0) = ptA(0)
        pt4(1) = pt4(1) + ply_seams(i)
        Set BlockRefObj = ThisDrawing.ModelSpace.InsertBlock(pt4, "VBA_PLY_SHEET", 1#, 1#, 1#, 0) 'Insert plywood sheets
        Call ChangeProp(BlockRefObj, "Distance1", ply_width_x)
        Call ChangeProp(BlockRefObj, "Distance2", ply_seams(i))
        
        If DrawB = True Then
            pt4(0) = ptB(0)
            Set BlockRefObj = ThisDrawing.ModelSpace.InsertBlock(pt4, "VBA_PLY_SHEET", 1#, 1#, 1#, 0) 'Insert plywood sheets
            Call ChangeProp(BlockRefObj, "Distance1", ply_width_y)
            Call ChangeProp(BlockRefObj, "Distance2", ply_seams(i))
        End If
    Next i
    If DrawW = True Then
        pt4(0) = ptW(0): pt4(1) = ptW(1)
        For i = 1 To UBound(ply_seams_win)
            pt4(1) = pt4(1) + ply_seams_win(i)
            Set BlockRefObj = ThisDrawing.ModelSpace.InsertBlock(pt4, "VBA_PLY_SHEET", 1#, 1#, 1#, 0) 'Insert plywood sheets
            Call ChangeProp(BlockRefObj, "Distance1", ply_width_w)
            Call ChangeProp(BlockRefObj, "Distance2", ply_seams_win(i))
            If Round(pt4(1) - ptW(1), 3) = Round(WinPos, 3) Then pt4(1) = pt4(1) + WinGap 'Create a visual gap in the plywood where the window seam occurs
        Next i
    End If
    
    ThisDrawing.ActiveLayer = ThisDrawing.Layers("FORM")
        'Draw screw heads
            'Side A
            ply_tot = 0
            For i = 1 To UBound(ply_seams)
                ply_tot = ply_tot + ply_seams(i)
                For j = 1 To UBound(stud_spacing_x)
                    pt29(0) = ptA(0) + ply_width_x + chamf_thk - stud_spacing_x(j) - 1.75: pt29(1) = ptA(1) + ply_tot - 2 'set a screw head below the ply seam for each location on ply_seams
                    Set BlockRefObj = ThisDrawing.ModelSpace.InsertBlock(pt29, "VBA_SCREW_HEAD", 1#, 1#, 1#, 0) 'Insert screw heads
                    If i <> UBound(ply_seams) Then
                        pt29(0) = ptA(0) + ply_width_x + chamf_thk - stud_spacing_x(j) - 1.75: pt29(1) = ptA(1) + ply_tot + 2 'set a screw head above the ply seam for each loc except the top
                        Set BlockRefObj = ThisDrawing.ModelSpace.InsertBlock(pt29, "VBA_SCREW_HEAD", 1#, 1#, 1#, 0) 'Insert screw heads
                    End If
                Next j
            Next i
            For j = 1 To UBound(stud_spacing_x) 'set screw heads at the bottom
                pt29(0) = ptA(0) + ply_width_x + chamf_thk - stud_spacing_x(j) - 1.75: pt29(1) = ptA(1) + 2
                Set BlockRefObj = ThisDrawing.ModelSpace.InsertBlock(pt29, "VBA_SCREW_HEAD", 1#, 1#, 1#, 0) 'Insert screw heads
            Next j
            'Add the text notes on the right if no side B
            If DrawB = False Then
                pt_blk(0) = ptA(0) + ply_width_x + chamf_thk - stud_spacing_x(1) - 1.75: pt_blk(1) = ptA(1) + ply_seams(1) - 2
                If ply_seams(1) < 48 And UBound(ply_seams) > 1 Then pt_blk(1) = pt_blk(1) + ply_seams(2) 'Move note up if ply_seams(1) is small enough that it overlaps with the other text note
                Set BlockRefObj = ThisDrawing.ModelSpace.InsertBlock(pt_blk, "VBA_ELEVATION_NOTES_SCREWS", 1#, 1#, 1#, 0)
                
                pt_blk(0) = ptA(0) + ply_width_x: pt_blk(1) = ptA(1)
                Set BlockRefObj = ThisDrawing.ModelSpace.InsertBlock(pt_blk, "VBA_ELEVATION_NOTES", 1#, 1#, 1#, 0)
            End If
            
            'Side B
            If DrawB = True Then
                ply_tot = 0
                For i = 1 To UBound(ply_seams)
                    ply_tot = ply_tot + ply_seams(i)
                    For j = 1 To UBound(stud_spacing_y)
                        pt29(0) = ptB(0) + ply_width_y + chamf_thk - stud_spacing_y(j) - 1.75: pt29(1) = ptB(1) + ply_tot - 2 'set a screw head below the ply seam for each location on ply_seams
                        Set BlockRefObj = ThisDrawing.ModelSpace.InsertBlock(pt29, "VBA_SCREW_HEAD", 1#, 1#, 1#, 0) 'Insert screw heads
                        If i <> UBound(ply_seams) Then
                            pt29(0) = ptB(0) + ply_width_y + chamf_thk - stud_spacing_y(j) - 1.75: pt29(1) = ptB(1) + ply_tot + 2 'set a screw head above the ply seam for each loc except the top
                            Set BlockRefObj = ThisDrawing.ModelSpace.InsertBlock(pt29, "VBA_SCREW_HEAD", 1#, 1#, 1#, 0) 'Insert screw heads
                        End If
                    Next j
                Next i
                For j = 1 To UBound(stud_spacing_y) 'set screw heads at the bottom
                    pt29(0) = ptB(0) + ply_width_y + chamf_thk - stud_spacing_y(j) - 1.75: pt29(1) = ptB(1) + 2
                    Set BlockRefObj = ThisDrawing.ModelSpace.InsertBlock(pt29, "VBA_SCREW_HEAD", 1#, 1#, 1#, 0) 'Insert screw heads
                Next j
                'Add the text notes on the right if no window, left side if there is a window and a B side
                If DrawW = False Then 'Right side
                    pt_blk(0) = ptB(0) + ply_width_y + chamf_thk - stud_spacing_y(1) - 1.75: pt_blk(1) = ptB(1) + ply_seams(1) - 2
                    If ply_seams(1) < 48 And UBound(ply_seams) > 1 Then pt_blk(1) = pt_blk(1) + ply_seams(2) 'Move note up if ply_seams(1) is small enough that it overlaps with the other text note
                    Set BlockRefObj = ThisDrawing.ModelSpace.InsertBlock(pt_blk, "VBA_ELEVATION_NOTES_SCREWS", 1#, 1#, 1#, 0)
                    pt_blk(0) = ptB(0) + ply_width_y: pt_blk(1) = ptB(1)
                    Set BlockRefObj = ThisDrawing.ModelSpace.InsertBlock(pt_blk, "VBA_ELEVATION_NOTES", 1#, 1#, 1#, 0)
                ElseIf DrawW = True Then 'Left side
                    pt_blk(0) = ptB(0) + ply_width_y + chamf_thk - stud_spacing_y(UBound(stud_spacing_y)) - 1.75: pt_blk(1) = ptB(1) + ply_seams(1) - 2
                    If ply_seams(1) < 48 And UBound(ply_seams) > 1 Then pt_blk(1) = pt_blk(1) + ply_seams(2) 'Move note up if ply_seams(1) is small enough that it overlaps with the other text note
                    Set BlockRefObj = ThisDrawing.ModelSpace.InsertBlock(pt_blk, "VBA_ELEVATION_NOTES_SCREWS_MIRRORED", 1#, 1#, 1#, 0)
                    pt_blk(0) = ptB(0) + ply_width_y: pt_blk(1) = ptB(1)
                    Set BlockRefObj = ThisDrawing.ModelSpace.InsertBlock(pt_blk, "VBA_ELEVATION_NOTES_MIRRORED", 1#, 1#, 1#, 0)
                    Call ChangeProp(BlockRefObj, "Distance1", y + 12)
                End If
            End If
            
            'Side W
            If DrawW = True Then
                ply_tot = 0
                For i = 1 To UBound(ply_seams_win)
                    ply_tot = ply_tot + ply_seams_win(i)
                    For j = 1 To UBound(stud_spacing_w)
                        pt29(0) = ptW(0) + ply_width_w + chamf_thk - stud_spacing_w(j) - 1.75: pt29(1) = ptW(1) + ply_tot - 2 'set a screw head below the ply seam for each location on ply_seams_win
                        If Round(ply_tot, 3) = Round(WinPos, 3) Then pt29(1) = pt29(1) - WinStudOff 'Move screws down where studs are held back at the window seam
                        If Round(ply_tot, 3) > Round(WinPos, 3) Then pt29(1) = pt29(1) + WinGap
                        Set BlockRefObj = ThisDrawing.ModelSpace.InsertBlock(pt29, "VBA_SCREW_HEAD", 1#, 1#, 1#, 0) 'Insert screw heads
                        If i <> UBound(ply_seams_win) Then
                            pt29(0) = ptW(0) + ply_width_w + chamf_thk - stud_spacing_w(j) - 1.75: pt29(1) = ptW(1) + ply_tot + 2 'set a screw head above the ply seam for each loc except the top
                            If Round(ply_tot, 3) = Round(WinPos, 3) Then
                                pt29(1) = pt29(1) + WinStudOff + WinGap 'Move screws up where studs are held back at the window seam
                            End If
                            If Round(ply_tot, 3) > Round(WinPos, 3) Then pt29(1) = pt29(1) + WinGap
                            Set BlockRefObj = ThisDrawing.ModelSpace.InsertBlock(pt29, "VBA_SCREW_HEAD", 1#, 1#, 1#, 0) 'Insert screw heads
                        End If
                    Next j
                Next i
                For j = 1 To UBound(stud_spacing_w) 'set screw heads at the bottom
                    pt29(0) = ptW(0) + ply_width_w + chamf_thk - stud_spacing_w(j) - 1.75: pt29(1) = ptW(1) + 2
                    Set BlockRefObj = ThisDrawing.ModelSpace.InsertBlock(pt29, "VBA_SCREW_HEAD", 1#, 1#, 1#, 0) 'Insert screw heads
                Next j
            End If

        
        'Draw chamfer
        pt18(0) = ptA(0) + ply_width_x: pt18(1) = ptA(1) + stud_base_gap
        Set BlockRefObj = ThisDrawing.ModelSpace.InsertBlock(pt18, "VBA_CHAMF", 1#, 1#, 1#, 0) 'Insert chamfer
        Call ChangeProp(BlockRefObj, "Distance1", z - stud_base_gap)
        
        If DrawB = True Then
            pt18(0) = ptB(0) + ply_width_y: pt18(1) = ptB(1) + stud_base_gap
            Set BlockRefObj = ThisDrawing.ModelSpace.InsertBlock(pt18, "VBA_CHAMF", 1#, 1#, 1#, 0) 'Insert chamfer
            Call ChangeProp(BlockRefObj, "Distance1", z - stud_base_gap)

        End If

        If DrawW = True Then
            pt18(0) = ptW(0) + ply_width_w: pt18(1) = ptW(1) + stud_base_gap
            Set BlockRefObj = ThisDrawing.ModelSpace.InsertBlock(pt18, "VBA_CHAMF", 1#, 1#, 1#, 0) 'Insert chamfer below window
            Call ChangeProp(BlockRefObj, "Distance1", WinPos - stud_base_gap)
            pt18(0) = ptW(0) + ply_width_w: pt18(1) = ptW(1) + WinPos + WinGap
            Set BlockRefObj = ThisDrawing.ModelSpace.InsertBlock(pt18, "VBA_CHAMF", 1#, 1#, 1#, 0) 'Insert chamfer on window
            Call ChangeProp(BlockRefObj, "Distance1", z - WinPos)
        End If
        
    'Draw elevation view (clamps) specifc items
        'Studs
        If window = False Then
            For i = 1 To n_studs_e
                pt20(0) = ptE(0) + stud_spacing_e(i): pt20(1) = ptE(1) + stud_base_gap
                Set BlockRefObj = ThisDrawing.ModelSpace.InsertBlock(pt20, stud_face_block, 1#, 1#, 1#, pi / 2) 'Insert studs
                Call ChangeProp(BlockRefObj, "Distance1", z - stud_base_gap): Call ChangeProp(BlockRefObj, "Visibility1", "Solid")
            Next i
        ElseIf window = True Then
            If DrawW = True Then
                For i = 1 To n_studs_e
                    pt20(0) = ptE(0) + stud_spacing_e(i): pt20(1) = ptE(1) + stud_base_gap
                    Set BlockRefObj = ThisDrawing.ModelSpace.InsertBlock(pt20, stud_face_block, 1#, 1#, 1#, pi / 2) 'Insert studs
                    Call ChangeProp(BlockRefObj, "Distance1", WinPos - stud_base_gap - WinStudOff): Call ChangeProp(BlockRefObj, "Visibility1", "Solid")
                    pt21(0) = ptE(0) + stud_spacing_e(i): pt21(1) = ptE(1) + WinPos + WinStudOff
                    Set BlockRefObj = ThisDrawing.ModelSpace.InsertBlock(pt21, stud_face_block, 1#, 1#, 1#, pi / 2) 'Insert studs
                    Call ChangeProp(BlockRefObj, "Distance1", z - WinPos - WinStudOff): Call ChangeProp(BlockRefObj, "Visibility1", "Solid")
                Next i
            End If
        End If
        
        'Plywood
        'Outer ply boundry of elevation view
        ThisDrawing.ActiveLayer = ThisDrawing.Layers("PLYA")
        Call DrawRectangle(ptE(0) + chamf_thk, ptE(1), ptE(0) + chamf_thk + ply_width_e, ptE(1) + z)
        
        'Plywood edge view
        Set BlockRefObj = ThisDrawing.ModelSpace.InsertBlock(ptE, "VBA_PLY", 1#, 1#, 1#, pi / 2)
        Call ChangeProp(BlockRefObj, "Distance1", z)
        
        'Plywood seam at window
        If window = True Then
            pt20(0) = ptE(0) + chamf_thk: pt20(1) = ptE(1) + WinPos
            pt21(0) = ptE(0) + ply_width_e + chamf_thk: pt21(1) = ptE(1) + WinPos
            Set LineObj = ThisDrawing.ModelSpace.AddLine(pt20, pt21)
        End If
        
        'Draw 2x2s for window lock
        If window = True Then
            ThisDrawing.ActiveLayer = ThisDrawing.Layers("0")
            If z - WinPos < 18 Then
                pt20(1) = ptE(1) + z
            Else
                pt20(1) = ptE(1) + WinPos + 18
            End If
            pt21(1) = pt20(1) - 36
            
            Dim Inserted2x2Note As Boolean: Inserted2x2Note = False
            For i = 1 To UBound(stud_spacing_w) - 1
                If stud_spacing_w(i + 1) - stud_spacing_w(i) - 3.5 > min_2x2_gap Then
                    pt20(0) = ptE(0) + stud_spacing_w(i) + 3.5
                    pt21(0) = pt20(0) + 1.5:
                    Call DrawRectangle(pt20(0), pt20(1), pt21(0), pt21(1))
                    
                    'Add text note under first clamp below window
                    If Inserted2x2Note = False Then
                        Inserted2x2Note = True
                        For j = 1 To n_clamps
                            If clamp_spacing_con(j) < WinPos Then
                                pt18(0) = ptE(0) + stud_spacing_w(UBound(stud_spacing_w) - 1) + 3.5 + 1.5
                                pt18(1) = ptE(1) + clamp_spacing_con(j) - 6
                                Set BlockRefObj = ThisDrawing.ModelSpace.InsertBlock(pt18, "VBA_2X2_NOTES", 1#, 1#, 1#, 0)
                                GoTo NoteInserted
                            End If
                        Next j
                    End If
NoteInserted:
                End If
            Next i
        End If
        
        'Clamps and dims
        ThisDrawing.ActiveLayer = ThisDrawing.Layers("FMTEXTA")
        pt21(0) = ptE(0) + chamf_thk + ply_width_e: pt21(1) = ptE(1) + z
        Call DrawDimLin(pt21(0) - clamp_L + 3.75, pt21(1) - clamp_spacing(1), ptE(0) - ply_thk, pt21(1), pt21(0) - clamp_L + 3.75 - 4, (pt21(1) * 2 - clamp_spacing(1)) / 2, pi / 2)     'Add top dim
        
        For i = 1 To n_clamps
            'Draw clamps and dims
            pt21(1) = pt21(1) - clamp_spacing(i)
            Set BlockRefObj = ThisDrawing.ModelSpace.InsertBlock(pt21, clamp_block_pr, 1#, 1#, 1#, 0) 'Insert clamp profile views
            Call ChangeProp(BlockRefObj, "Distance1", 1.5 + ply_thk + chamf_thk + ply_width_e)
            If i <> 1 Then
                Call DrawDim(pt21(0) - clamp_L + 3.75, pt21(1), pt21(0) - clamp_L + 3.75, pt21(1) + clamp_spacing(i), pt21(0) - clamp_L + 3.75 - 4, (pt21(1) * 2 + clamp_spacing(i)) / 2)
            End If
            
            'Draw inches from bottom
            pt22(0) = pt21(0) - clamp_L + 3.75 - 12: pt22(1) = ptE(1) + clamp_spacing_con(i) + 1.5
            clamp_str = CStr(clamp_spacing_con(i)) & """"
            Set MTextObject2 = ThisDrawing.ModelSpace.AddMText(pt22, 9, clamp_str)
            MTextObject2.Height = 2.5
            
            'Draw "CLAMP" and "TOP CLAMP" labels
            pt25(0) = ptE(0) + chamf_thk + ply_width_e + 9: pt25(1) = pt21(1) + 5.75 - 3 * Abs(WinY = True)
            
            If clamp_size = 1 And ply_width_e - 1.5 >= 19 Then
                pt25(1) = pt25(1) - 3
            ElseIf clamp_size = 2 And ply_width_e - 1.5 >= 31 Then
                pt25(1) = pt25(1) - 3
            ElseIf clamp_size = 3 And ply_width_e - 1.5 >= 43 Then
                pt25(1) = pt25(1) - 3
            End If
            
            If i <= n_top_clamps Then
                Set MTextObject2 = ThisDrawing.ModelSpace.AddMText(pt25, 24, "TOP CLAMP")
            Else
                Set MTextObject2 = ThisDrawing.ModelSpace.AddMText(pt25, 17, "CLAMP")
            End If
            MTextObject2.AttachmentPoint = acAttachmentPointTopLeft
            MTextObject2.Height = 2.5
        Next i
        Call DrawDimLin(pt21(0) - clamp_L + 3.75, ptE(1) + bot_clamp_gap, pt21(0) - x - 8, ptE(1), pt21(0) - clamp_L + 3.75 - 4, (2 * ptE(1) + bot_clamp_gap) / 2, pi / 2) 'Add bottom dim
        
        'Draw 36" coil rod and nuts connecting top 2 clamps if column is tall enough
        If n_top_clamps >= 2 Or SquaringCornerOptionPickingButton.Value = True Then
            pt27(0) = ptE(0) + chamf_thk + 2: pt27(1) = ptE(1) + z - clamp_spacing(1) + 2.25 - 0.5 * Abs(WinY = True)
            Set BlockRefObj = ThisDrawing.ModelSpace.InsertBlock(pt27, "VBA_COIL_ROD", 1#, 1#, 1#, pi)
            If ply_width_w >= 37.5 Then
                Set BlockRefObj = ThisDrawing.ModelSpace.InsertBlock(pt27, "VBA_COIL_ROD_NOTES", 1#, 1#, 1#, 0)
            ElseIf SquaringCornerOptionPickingButton.Value = True Then
                Set BlockRefObj = ThisDrawing.ModelSpace.InsertBlock(pt27, "VBA_COIL_ROD_NOTES_C", 1#, 1#, 1#, 0)
                Call ChangeProp(BlockRefObj, "Distance1", Abs(40 - (36 - ply_width_e)))
            Else
                Set BlockRefObj = ThisDrawing.ModelSpace.InsertBlock(pt27, "VBA_COIL_ROD_NOTES_B", 1#, 1#, 1#, 0)
            End If
            pt27(1) = pt27(1) - 2
            Set BlockRefObj = ThisDrawing.ModelSpace.InsertBlock(pt27, "VBA_NUT_5-8", 1#, 1#, 1#, 0)
            pt27(1) = pt27(1) - 0.25
            Set BlockRefObj = ThisDrawing.ModelSpace.InsertBlock(pt27, "VBA_NUT_5-8", 1#, 1#, 1#, pi)
            pt27(1) = pt27(1) - clamp_spacing(2)
            Set BlockRefObj = ThisDrawing.ModelSpace.InsertBlock(pt27, "VBA_NUT_5-8", 1#, 1#, 1#, pi)
            pt27(1) = pt27(1) + 0.25
            Set BlockRefObj = ThisDrawing.ModelSpace.InsertBlock(pt27, "VBA_NUT_5-8", 1#, 1#, 1#, 0)
        End If
        
        'Draw 14" coil rod and nuts connecting clamps around window seam
        If window = True Then
            'If there's a 36" rod, check if it's bolting the same clamps as the 14" rod.
            If n_top_clamps >= 2 Or SquaringCornerOptionPickingButton.Value = True Then
                'Don't add this if the 36" coil rod is also bolting the window clamps
                If clamp_spacing_con(2) > WinPos Then
Draw14InRodAnways:
                    pt27(0) = ptE(0) + chamf_thk + ply_width_w / 2: pt27(1) = ptE(1) + WinPos + win_clamp_top_max + 2.625 - 0.5 * Abs(WinY = True)
                    Set BlockRefObj = ThisDrawing.ModelSpace.InsertBlock(pt27, "VBA_COIL_ROD_14", 1#, 1#, 1#, pi)
                    Set BlockRefObj = ThisDrawing.ModelSpace.InsertBlock(pt27, "VBA_COIL_ROD_NOTES_14", 1#, 1#, 1#, 0)
                    Call ChangeProp(BlockRefObj, "Distance1", Abs(clamp_spacing_con(1) - clamp_spacing_con(2) - 12))
                    pt27(1) = pt27(1) - 2.375
                    Set BlockRefObj = ThisDrawing.ModelSpace.InsertBlock(pt27, "VBA_NUT_5-8", 1#, 1#, 1#, 0)
                    pt27(1) = pt27(1) - 0.25
                    Set BlockRefObj = ThisDrawing.ModelSpace.InsertBlock(pt27, "VBA_NUT_5-8", 1#, 1#, 1#, pi)
                    pt27(1) = pt27(1) - win_clamp_top_max - win_clamp_bot_max + 0.25
                    Set BlockRefObj = ThisDrawing.ModelSpace.InsertBlock(pt27, "VBA_NUT_5-8", 1#, 1#, 1#, 0)
                    pt27(1) = pt27(1) - 0.25
                    Set BlockRefObj = ThisDrawing.ModelSpace.InsertBlock(pt27, "VBA_NUT_5-8", 1#, 1#, 1#, pi)
                End If
            Else
                GoTo Draw14InRodAnways
            End If
        End If
        
        'Draw reinforcing angle on all clamps at or below 87" from top of column on elevation veiw.
        If x > 40 Then
            For i = 1 To UBound(clamp_spacing_con) - 1 'Last value is a 0
                If (z - clamp_spacing_con(i)) >= 87 Then
                    If WinY = True Then 'Flip and raise reinforcing angle when displayed on Y side of clamp in elevation view
                        pt31(0) = ptE(0) + chamf_thk + (ply_width_e - 36) / 2 + 36
                        pt31(1) = ptE(1) + clamp_spacing_con(i) - 0.25
                        Set BlockRefObj = ThisDrawing.ModelSpace.InsertBlock(pt31, "VBA_REINFORCING_ANGLE", 1#, 1#, 1#, pi)
                    Else
                        pt31(0) = ptE(0) + chamf_thk + (ply_width_e - 36) / 2
                        pt31(1) = ptE(1) + clamp_spacing_con(i)
                        Set BlockRefObj = ThisDrawing.ModelSpace.InsertBlock(pt31, "VBA_REINFORCING_ANGLE", 1#, 1#, 1#, 0)
                    End If
                    
                End If
            Next i
        End If
        
        'Lifting slings
        If SquaringCornerOptionRegularButton.Value = True Then
            pt26(0) = ptE(0) - ply_thk - 1.25: pt26(1) = ptE(1) + z - clamp_spacing(1)
            Set BlockRefObj = ThisDrawing.ModelSpace.InsertBlock(pt26, "VBA_LIFTING_SLING_A", 1#, 1#, 1#, 0) 'Insert left sling
            pt26(0) = ptE(0) + chamf_thk + ply_width_e + 1.3: pt26(1) = ptE(1) + z - clamp_spacing(1) + 3
            Set BlockRefObj = ThisDrawing.ModelSpace.InsertBlock(pt26, "VBA_LIFTING_SLING_B", 1#, 1#, 1#, 0) 'Insert right sling
        ElseIf SquaringCornerOptionPickingButton.Value = True Then
            pt26(0) = ptE(0) - ply_thk - 1.5: pt26(1) = ptE(1) + z - clamp_spacing(1) - 0.25
            Set BlockRefObj = ThisDrawing.ModelSpace.InsertBlock(pt26, "VBA_LIFTING_CORNER_A", 1#, 1#, 1#, 0) 'Insert left sling
            pt26(0) = ptE(0) + chamf_thk + ply_width_e: pt26(1) = ptE(1) + z - clamp_spacing(1) - 0.25
            Set BlockRefObj = ThisDrawing.ModelSpace.InsertBlock(pt26, "VBA_LIFTING_CORNER_B", 1#, 1#, 1#, 0) 'Insert right sling
        End If
        
        'AFB
        pt28(0) = ptE(0) + chamf_thk + ply_width_e + 4: pt28(1) = ptE(1) + clamp_spacing_con(brace_clamp)
        Set BlockRefObj = ThisDrawing.ModelSpace.InsertBlock(pt28, "VBA_AFB_SIDE", 1#, 1#, 1#, 0) 'Insert AFB side view
        
        pt28(0) = pt28(0) + 1.9375: pt28(1) = pt28(1) + 0.6789
        Set BlockRefObj = ThisDrawing.ModelSpace.InsertBlock(pt28, "VBA_BRACE_ANGLE", 1#, 1#, 1#, 0) 'Insert brace angle
        Set BlockRefObj = ThisDrawing.ModelSpace.InsertBlock(pt28, brace_block, 1#, 1#, 1#, 0) 'Insert brace dynamic block
        Set BlockRefObj = ThisDrawing.ModelSpace.InsertBlock(pt28, "VBA_BRACE_NOTES", 1#, 1#, 1#, 0) 'Insert brace notes
        
        'Insert safety chain block and note, stretch note if the block is placed too low and will conflict with "VBA_ELEVATION_NOTES_MIRRORED"
        pt28(0) = pt28(0) - 5.9375: pt28(1) = ptE(1) + clamp_spacing_con(chain_clamp)
        Set BlockRefObj = ThisDrawing.ModelSpace.InsertBlock(pt28, "VBA_CHAIN", 1#, 1#, 1#, 0)
        If pt28(1) - pt_o(1) < 62 Then
            Call ChangeProp(BlockRefObj, "Distance1", 6.27 + 62 - (pt28(1) - pt_o(1)))
        End If
        
        pt28(0) = ptE(0) + 4.68: pt28(1) = ptE(1) + clamp_spacing_con(brace_clamp)
        If window = False Then
            Set BlockRefObj = ThisDrawing.ModelSpace.InsertBlock(pt28, "VBA_AFB_FACE", 1#, 1#, 1#, 0) 'Insert AFB face view
        End If
        
        ThisDrawing.ActiveLayer = ThisDrawing.Layers("FORM")

        'Base framing lumber
        pt20(0) = ptE(0) - ply_thk - 1.5 - 3.5: pt20(1) = ptE(1)
        Set BlockRefObj = ThisDrawing.ModelSpace.InsertBlock(pt20, "VBA_2X4", 1#, 1#, 1#, 0) 'Insert studs
        pt20(0) = ptE(0) + chamf_thk + ply_width_e: pt20(1) = ptE(1)
        Set BlockRefObj = ThisDrawing.ModelSpace.InsertBlock(pt20, "VBA_2X4", 1#, 1#, 1#, 0) 'Insert studs
        pt20(0) = ptE(0) - ply_thk - 1.5 - 6: pt20(1) = ptE(1) + 3
        Set BlockRefObj = ThisDrawing.ModelSpace.InsertBlock(pt20, "VBA_2X4_SIDE", 1#, 1#, 1#, 0) 'Insert studs
        Call ChangeProp(BlockRefObj, "Distance1", ply_width_e + chamf_thk + ply_thk + 1.5 + 12)
        pt30(0) = ptE(0) + chamf_thk + ply_width_e + 6: pt30(1) = ptE(1) + 2.25
        Set BlockRefObj = ThisDrawing.ModelSpace.InsertBlock(pt30, "VBA_DOWN_PLATE_NOTES", 1#, 1#, 1#, 0)
    
    'Draw panel sections
        'Side A
        pt8(0) = ptA(0) + ply_width_x: pt8(1) = ptA(1) + z + 18 + Abs(window) * WinGap
        Set BlockRefObj = ThisDrawing.ModelSpace.InsertBlock(pt8, "VBA_PLY_WITH_CHAMFER", 1#, 1#, 1#, pi) 'Insert ply with chamfer
        Call ChangeProp(BlockRefObj, "Distance1", ply_width_x)
        For i = 1 To n_studs_x
            pt11(0) = ptA(0) + ply_width_x + chamf_thk - 3.5 - stud_spacing_x(i)
            pt11(1) = ptA(1) + z + 18 + Abs(window) * WinGap
            Set BlockRefObj = ThisDrawing.ModelSpace.InsertBlock(pt11, stud_block, 1#, 1#, 1#, 0) 'Insert studs
        Next i
        
        'Side B
        If DrawB = True Then
            pt9(0) = ptB(0) + ply_width_y: pt9(1) = ptB(1) + z + 18 + Abs(window) * WinGap
            Set BlockRefObj = ThisDrawing.ModelSpace.InsertBlock(pt9, "VBA_PLY_WITH_CHAMFER", 1#, 1#, 1#, pi) 'Insert ply with chamfer
            Call ChangeProp(BlockRefObj, "Distance1", ply_width_y)
            For i = 1 To n_studs_y
                pt11(0) = ptB(0) + ply_width_y + chamf_thk - 3.5 - stud_spacing_y(i)
                pt11(1) = ptB(1) + z + 18 + Abs(window) * WinGap
                Set BlockRefObj = ThisDrawing.ModelSpace.InsertBlock(pt11, stud_block, 1#, 1#, 1#, 0) 'Insert studs
            Next i
        End If

        'Side W
        If DrawW = True Then
            pt10(0) = ptW(0) + ply_width_w: pt10(1) = ptW(1) + z + 18 + Abs(window) * WinGap
            Set BlockRefObj = ThisDrawing.ModelSpace.InsertBlock(pt10, "VBA_PLY_WITH_CHAMFER", 1#, 1#, 1#, pi) 'Insert ply with chamfer
            Call ChangeProp(BlockRefObj, "Distance1", ply_width_w)
            For i = 1 To n_studs_w
                pt11(0) = ptW(0) + ply_width_w + chamf_thk - 3.5 - stud_spacing_w(i)
                pt11(1) = ptW(1) + z + 18 + Abs(window) * WinGap
                Set BlockRefObj = ThisDrawing.ModelSpace.InsertBlock(pt11, stud_block, 1#, 1#, 1#, 0) 'Insert studs
            Next i
        End If
        
        'Dim sections
            'Side A
            Call DrawDim(pt8(0), pt8(1) - ply_thk, pt8(0) - ply_width_x, pt8(1) - ply_thk, (pt8(0) - ply_width_x - pt8(0)) / 2, pt8(1) - ply_thk - 3) 'Dimension plywood
            Call DrawDimLin(pt8(0) + chamf_thk, pt8(1) - ply_thk - 0.5, pt8(0) - ply_width_x, pt8(1) - ply_thk, (pt8(0) - ply_width_x - pt8(0)) / 2, pt8(1) - ply_thk - 6.75, 0) 'Dimension overall panel
            For i = 1 To n_studs_x
                Call DrawDimLin(pt8(0) + chamf_thk - stud_spacing_x(UBound(stud_spacing_x) - i + 1), pt8(1) + 1.5, pt8(0) - ply_width_x, pt8(1), ((pt8(0) - ply_width_x) - (pt8(0) + chamf_thk - stud_spacing_x(UBound(stud_spacing_x) - i + 1))) / 2, pt8(1) + 4 + i * 4, 0) 'Dimension studs from rightmost (in plan) stud
            Next i
            Call DrawDimLin(pt8(0) - stud_spacing_x(UBound(stud_spacing_x)) - 3.5 + chamf_thk, pt8(1) + 1.5, pt8(0) - ply_width_x, pt8(1), ((pt8(0) - ply_width_x) - (pt8(0) - stud_spacing_x(UBound(stud_spacing_x)) - 3.5 + chamf_thk)) / 2, pt8(1) + 4, 0) 'Dimension leftmost (in plan) stud to face of ply
            Call DrawDimLin(pt8(0) + chamf_thk - stud_start_offset, pt8(1) + 1.5, pt8(0) + chamf_thk, pt8(1), ((pt8(0) + chamf_thk) - (pt8(0) + chamf_thk - stud_start_offset)) / 2, pt8(1) + 4 * (n_studs_x + 1), 0) 'dimension stud_start_gap
            
            'Side B
            If DrawB = True Then
                Call DrawDim(pt9(0), pt9(1) - ply_thk, pt9(0) - ply_width_y, pt9(1) - ply_thk, (pt9(0) - ply_width_y - pt9(0)) / 2, pt9(1) - ply_thk - 3) 'Dimension plywood
                Call DrawDimLin(pt9(0) + chamf_thk, pt9(1) - ply_thk - 0.5, pt9(0) - ply_width_y, pt9(1) - ply_thk, (pt9(0) - ply_width_y - pt9(0)) / 2, pt9(1) - ply_thk - 6.75, 0) 'Dimension overall panel
                For i = 1 To n_studs_y
                    Call DrawDimLin(pt9(0) + chamf_thk - stud_spacing_y(UBound(stud_spacing_y) - i + 1), pt9(1) + 1.5, pt9(0) - ply_width_y, pt9(1), ((pt9(0) - ply_width_y) - (pt9(0) + chamf_thk - stud_spacing_y(UBound(stud_spacing_y) - i + 1))) / 2, pt9(1) + 4 + i * 4, 0) 'Dimension studs from rightmost (in plan) stud
                Next i
                Call DrawDimLin(pt9(0) - stud_spacing_y(UBound(stud_spacing_y)) - 3.5 + chamf_thk, pt9(1) + 1.5, pt9(0) - ply_width_y, pt9(1), ((pt9(0) - ply_width_y) - (pt9(0) - stud_spacing_y(UBound(stud_spacing_y)) - 3.5 + chamf_thk)) / 2, pt9(1) + 4, 0) 'Dimension leftmost (in plan) stud to face of ply
                Call DrawDimLin(pt9(0) + chamf_thk - stud_start_offset, pt9(1) + 1.5, pt9(0) + chamf_thk, pt9(1), ((pt9(0) + chamf_thk) - (pt9(0) + chamf_thk - stud_start_offset)) / 2, pt9(1) + 4 * (n_studs_y + 1), 0) 'dimension stud_start_gap

                Set BlockRefObj = ThisDrawing.ModelSpace.InsertBlock(pt9, "VBA_TOP_SECTION_DETAILS1", 1#, 1#, 1#, 0) 'Insert text notes, blow up detail at top section
            End If
            
            'Side W
            If DrawW = True Then
                Call DrawDim(pt10(0), pt10(1) - ply_thk, pt10(0) - ply_width_w, pt10(1) - ply_thk, (pt10(0) - ply_width_w - pt10(0)) / 2, pt10(1) - ply_thk - 3) 'Dimension plywood
                Call DrawDimLin(pt10(0) + chamf_thk, pt10(1) - ply_thk - 0.5, pt10(0) - ply_width_w, pt10(1) - ply_thk, (pt10(0) - ply_width_w - pt10(0)) / 2, pt10(1) - ply_thk - 6.75, 0) 'Dimension overall panel
                For i = 1 To n_studs_w
                    Call DrawDimLin(pt10(0) + chamf_thk - stud_spacing_w(UBound(stud_spacing_w) - i + 1), pt10(1) + 1.5, pt10(0) - ply_width_w, pt10(1), ((pt10(0) - ply_width_w) - (pt10(0) + chamf_thk - stud_spacing_w(UBound(stud_spacing_w) - i + 1))) / 2, pt10(1) + 4 + i * 4, 0) 'Dimension studs from rightmost (in plan) stud
                Next i
                Call DrawDimLin(pt10(0) - stud_spacing_w(UBound(stud_spacing_w)) - 3.5 + chamf_thk, pt10(1) + 1.5, pt10(0) - ply_width_w, pt10(1), ((pt10(0) - ply_width_w) - (pt10(0) - stud_spacing_w(UBound(stud_spacing_w)) - 3.5 + chamf_thk)) / 2, pt10(1) + 4, 0) 'Dimension leftmost (in plan) stud to face of ply
                Call DrawDimLin(pt10(0) + chamf_thk - stud_start_offset, pt10(1) + 1.5, pt10(0) + chamf_thk, pt10(1), ((pt10(0) + chamf_thk) - (pt10(0) + chamf_thk - stud_start_offset)) / 2, pt10(1) + 4 * (n_studs_w + 1), 0) 'dimension stud_start_gap
            End If
            
        'Dim plywood
            'Side A
            PlyTemp = ptA(1) + ply_seams(1)
            Call DrawDimSuffix(ptA(0) + ply_width_x, ptA(1), ptA(0) + ply_width_x, PlyTemp, ptA(0) + ply_width_x + 6, (PlyTemp - ptA(1)) / 2, " PLYWOOD")
            If UBound(ply_seams) >= 2 Then 'If more than one ply panel, draw the rest, bottom up
                For i = 2 To UBound(ply_seams)
                    PlyTemp = PlyTemp + ply_seams(i)
                    Call DrawDimSuffix(ptA(0) + ply_width_x, PlyTemp - ply_seams(i), ptA(0) + ply_width_x, PlyTemp, ptA(0) + ply_width_x + 6, (PlyTemp - (PlyTemp - ply_seams(i))) / 2, " PLYWOOD")
                Next i
            End If
            Call DrawDimSuffix(ptA(0), ptA(1), ptA(0), ptA(1) + z, ptA(0) - 9, (2 * ptA(1) + z) / 2, " OVERALL HEIGHT")
            Call DrawDimSuffix(ptA(0), ptA(1) + z, ptA(0), ptA(1) + stud_base_gap, ptA(0) - 4.5, ((ptA(1) + z) + (ptA(1) + stud_base_gap)) / 2, " STUD")
            Call DrawDimSuffix(ptA(0) + ply_width_x, ptA(1) + z, ptA(0), ptA(1) + z, (2 * ptA(0) + ply_width_x) / 2, ptA(1) + z + 4, " PLYWOOD")
            
            'Side B
            If DrawB = True Then
                PlyTemp = ptB(1) + ply_seams(1)
                Call DrawDimSuffix(ptB(0) + ply_width_y, ptB(1), ptB(0) + ply_width_y, PlyTemp, ptB(0) + ply_width_y + 6, (PlyTemp - ptB(1)) / 2, " PLYWOOD")
                If UBound(ply_seams) >= 2 Then 'If more than one ply panel, draw the rest, bottom up
                    For i = 2 To UBound(ply_seams)
                        PlyTemp = PlyTemp + ply_seams(i)
                        Call DrawDimSuffix(ptB(0) + ply_width_y, PlyTemp - ply_seams(i), ptB(0) + ply_width_y, PlyTemp, ptB(0) + ply_width_y + 6, (PlyTemp - (PlyTemp - ply_seams(i))) / 2, " PLYWOOD")
                    Next i
                End If
                Call DrawDimSuffix(ptB(0), ptB(1), ptB(0), ptB(1) + z, ptB(0) - 9, (2 * ptB(1) + z) / 2, " OVERALL HEIGHT")
                Call DrawDimSuffix(ptB(0), ptB(1) + z, ptB(0), ptB(1) + stud_base_gap, ptB(0) - 4.5, ((ptB(1) + z) + (ptB(1) + stud_base_gap)) / 2, " STUD")
                Call DrawDimSuffix(ptB(0) + ply_width_y, ptB(1) + z, ptB(0), ptB(1) + z, (2 * ptB(0) + ply_width_y) / 2, ptB(1) + z + 4, " PLYWOOD")
            End If
            
            'Side W
            If DrawW = True Then
                PlyTemp = ptW(1) + ply_seams_win(1)
                Call DrawDimSuffix(ptW(0) + ply_width_w, ptW(1), ptW(0) + ply_width_w, PlyTemp, ptW(0) + ply_width_w + 6, (PlyTemp - ptW(1)) / 2, " PLYWOOD") 'Dim lowest (first) plywood sheet
                If UBound(ply_seams_win) >= 2 Then 'If more than one ply panel, draw the rest, bottom up
                    For i = 2 To UBound(ply_seams_win)
                        
                        If Round(PlyTemp - ptW(1), 3) = Round(WinPos, 3) Then PlyTemp = PlyTemp + WinGap 'Add the window gap distance when it's reached
                        PlyTemp = PlyTemp + ply_seams_win(i)
                        
                        'Pop out dimension if less than 26"
                        If Round(ply_seams_win(i), 3) < 26 Then
                            Call DrawDimLinSuffixLeader(ptW(0) + ply_width_w, PlyTemp - ply_seams_win(i), ptW(0) + ply_width_w, PlyTemp, ptW(0) + ply_width_w + 6, (PlyTemp + (PlyTemp - ply_seams_win(i))) / 2, ptW(0) + ply_width_w + 11, 4 + (PlyTemp + (PlyTemp - ply_seams_win(i))) / 2, " PLYWOOD", pi / 2)
                        Else
                            Call DrawDimSuffix(ptW(0) + ply_width_w, PlyTemp - ply_seams_win(i), ptW(0) + ply_width_w, PlyTemp, ptW(0) + ply_width_w + 6, (PlyTemp + (PlyTemp - ply_seams_win(i))) / 2, " PLYWOOD")
                        End If
                        
                    Next i
                End If
                Call DrawDimSuffix(ptW(0), ptW(1) + WinPos - WinStudOff, ptW(0), ptW(1) + stud_base_gap, ptW(0) - 4.5, (ptW(1) + WinPos - WinStudOff + ptW(1) + stud_base_gap) / 2, " STUD") 'lower stud
                Call DrawDimSuffix(ptW(0), ptW(1) + WinPos + WinStudOff + WinGap, ptW(0), ptW(1) + z + WinGap, ptW(0) - 4.5, (ptW(1) + z + ptW(1) + WinPos + WinStudOff + 2 * WinGap) / 2, " STUD") 'window stud
                Call DrawDimLinLeader(ptW(0), ptW(1) + WinPos - WinStudOff, ptW(0), ptW(1) + WinPos, ptW(0) - 4.5, (ptW(1) + WinPos - WinStudOff + ptW(1) + WinPos) / 2, ptW(0) - 8.5, ptW(1) + WinPos - 5.5, pi / 2) 'Lower stud offset dimension
                Call DrawDimLinLeader(ptW(0), ptW(1) + WinPos + WinStudOff + WinGap, ptW(0), ptW(1) + WinPos + WinGap, ptW(0) - 4.5, (ptW(1) + WinPos + WinStudOff + ptW(1) + WinPos + 2 * WinGap) / 2, ptW(0) - 8.5, ptW(1) + WinPos + WinGap + 5.5, pi / 2) 'window stud offset dimension
                Call DrawDimSuffix(ptW(0) + ply_width_w, ptW(1) + z + WinGap, ptW(0), ptW(1) + z + WinGap, (2 * ptW(0) + ply_width_w) / 2, ptW(1) + z + 4 + WinGap, " PLYWOOD")
            End If

            'Dim window seam to clamps on elevation view
            If window = True Then
                Call DrawDimLin(ptE(0) + chamf_thk, ptE(1) + WinPos, ptE(0) + chamf_thk, ptE(1) + WinPos + win_clamp_top_max, ptE(0) - 4.5, (2 * ptE(1) + 2 * WinPos + win_clamp_top_max) / 2, pi / 2)
                Call DrawDimLin(ptE(0) + chamf_thk, ptE(1) + WinPos, ptE(0) + chamf_thk, ptE(1) + WinPos - win_clamp_bot_max, ptE(0) - 4.5, (2 * ptE(1) + 2 * WinPos - win_clamp_bot_max) / 2, pi / 2)
            End If
            
    'PLAN VIEWS
    pt13(0) = pt_o(0) + 427 + x - chamf_thk: pt13(1) = pt_o(1) + 42 + ply_thk 'origin point for plan views
    
    'Draw elevation sight [REMOVED]
    'pt33(0) = pt13(0) - x / 2: pt33(1) = pt13(1) + 83.5 - 16
    'Set BlockRefObj = ThisDrawing.ModelSpace.InsertBlock(pt33, "VBA_ELEV_C", 1#, 1#, 1#, 0) 'Elevation C for clamps

    'Draw text notes
        'clamps
        pt30(0) = pt13(0) - x: pt30(1) = pt13(1) + y
        Set BlockRefObj = ThisDrawing.ModelSpace.InsertBlock(pt30, "VBA_PLAN_NOTES1", 1#, 1#, 1#, 0)
        pt30(0) = pt13(0): pt30(1) = pt13(1)
        Set BlockRefObj = ThisDrawing.ModelSpace.InsertBlock(pt30, "VBA_PLAN_NOTES2", 1#, 1#, 1#, 0)
        pt30(0) = pt13(0): pt30(1) = pt13(1) + y
        Set BlockRefObj = ThisDrawing.ModelSpace.InsertBlock(pt30, "VBA_PLAN_NOTES3", 1#, 1#, 1#, 0)
        pt30(0) = pt13(0) - x: pt30(1) = pt13(1)
        Set BlockRefObj = ThisDrawing.ModelSpace.InsertBlock(pt30, "VBA_PLAN_NOTES4", 1#, 1#, 1#, 0)
        
        'top clamps
        pt30(0) = pt13(0) - x: pt30(1) = pt13(1) + y + 83.5
        Set BlockRefObj = ThisDrawing.ModelSpace.InsertBlock(pt30, "VBA_PLAN_NOTES5", 1#, 1#, 1#, 0)
        pt30(0) = pt13(0) - (x - 12) / 2: pt30(1) = pt13(1) + y + 83.5
        Set BlockRefObj = ThisDrawing.ModelSpace.InsertBlock(pt30, "VBA_PLAN_NOTES6", 1#, 1#, 1#, 0)
        pt30(0) = pt13(0) - x: pt30(1) = pt13(1) + 83.5
        If SquaringCornerOptionPickingButton.Value = True Then
            Set BlockRefObj = ThisDrawing.ModelSpace.InsertBlock(pt30, "VBA_PLAN_NOTES7_LOOP", 1#, 1#, 1#, 0)
        Else
            Set BlockRefObj = ThisDrawing.ModelSpace.InsertBlock(pt30, "VBA_PLAN_NOTES7", 1#, 1#, 1#, 0)
        End If
        
    'Draw clamps
    pt15(0) = pt13(0): pt15(1) = pt13(1)
    Set BlockRefObj = ThisDrawing.ModelSpace.InsertBlock(pt15, clamp_block_op, 1#, 1#, 1#, 0) 'Insert clamp (operator typical clamps)
    pt15(0) = pt13(0) - x: pt15(1) = pt13(1) + y
    Set BlockRefObj = ThisDrawing.ModelSpace.InsertBlock(pt15, clamp_block_bk, 1#, 1#, 1#, 0) 'Insert clamp (back top clamps)
    pt15(0) = pt13(0): pt15(1) = pt13(1) + 83.5
    Set BlockRefObj = ThisDrawing.ModelSpace.InsertBlock(pt15, clamp_block_op, 1#, 1#, 1#, 0) 'Insert clamp (operator top clamps)
    If window = True Then Call ChangeProp(BlockRefObj, "Distance1", 2.5 + clamp_L - 12 - y) 'Rotate clamp out if window
    If window = True Then Call ChangeProp(BlockRefObj, "Angle1", swing_ang) 'Rotate clamp out if window
    pt15(0) = pt13(0) - x: pt15(1) = pt13(1) + y + 83.5
    Set BlockRefObj = ThisDrawing.ModelSpace.InsertBlock(pt15, clamp_block_bk, 1#, 1#, 1#, 0) 'Insert clamp (back typical clamps)

    'Draw squaring corners and slings for typical clamps
    pt15(0) = pt13(0) - x: pt15(1) = pt13(1)
    Set BlockRefObj = ThisDrawing.ModelSpace.InsertBlock(pt15, SQ_NAME, 1#, 1#, 1#, 0)
    pt15(0) = pt13(0): pt15(1) = pt13(1) + y
    Set BlockRefObj = ThisDrawing.ModelSpace.InsertBlock(pt15, SQ_NAME, 1#, 1#, 1#, pi)

    If SquaringCornerOptionRegularButton.Value = True Then
        'Lifting slings for top clamps (regular squaring corners)
        pt15(0) = pt13(0) - x: pt15(1) = pt13(1) + 83.5
        Set BlockRefObj = ThisDrawing.ModelSpace.InsertBlock(pt15, SQ_NAME_SLINGS, 1#, 1#, 1#, 0)
        pt15(0) = pt13(0): pt15(1) = pt13(1) + y + 83.5
        If window = False Then
            Set BlockRefObj = ThisDrawing.ModelSpace.InsertBlock(pt15, SQ_NAME_SLINGS, 1#, 1#, 1#, pi)
        End If
        
        'Add slings to studs for small columns where corner is inversed and sling isn't included at the corner OR for windows
        If Round(x, 3) < 14 Or Round(y, 3) < 14 Or window = True Then
            pt15(0) = pt13(0): pt15(1) = pt13(1) + 83.5 + y
            Set BlockRefObj = ThisDrawing.ModelSpace.InsertBlock(pt15, "VBA_LIFTING_SLING_C", 1#, 1#, 1#, 0)
            pt15(0) = pt13(0) - x: pt15(1) = pt13(1) + 83.5
            Set BlockRefObj = ThisDrawing.ModelSpace.InsertBlock(pt15, "VBA_LIFTING_SLING_C", 1#, 1#, 1#, pi)
        End If
    ElseIf SquaringCornerOptionPickingButton.Value = True Then
        'Lifting slings for top clamps (picking loops)
        pt15(0) = pt13(0) - x: pt15(1) = pt13(1) + 83.5
        Set BlockRefObj = ThisDrawing.ModelSpace.InsertBlock(pt15, "VBA_PICKING_CORNER", 1#, 1#, 1#, 0)
        pt15(0) = pt13(0): pt15(1) = pt13(1) + y + 83.5
        If window = False Then
            Set BlockRefObj = ThisDrawing.ModelSpace.InsertBlock(pt15, "VBA_PICKING_CORNER", 1#, 1#, 1#, pi)
        End If
    End If
    'Add sling notes
    If Round(x, 3) >= 14 And Round(y, 3) >= 14 Then
        pt15(0) = pt13(0): pt15(1) = pt13(1) + y + 83.5 'for columns where squaring corners not rotated (normal)
    Else
        pt15(0) = pt13(0) + 6: pt15(1) = pt13(1) - 1 + 83.5 'for columns where squaring corners are rotated, sling is tied between studs
    End If
    If window = False Then
        Set BlockRefObj = ThisDrawing.ModelSpace.InsertBlock(pt15, "VBA_PLAN_NOTES8", 1#, 1#, 1#, 0)
    End If
    
    'Draw plywood & chamfer
        ' "Clamps" ply & chamfer
        pt12(0) = pt13(0) - x + chamf_thk: pt12(1) = pt13(1) - ply_thk
        Set BlockRefObj = ThisDrawing.ModelSpace.InsertBlock(pt12, "VBA_PLY_WITH_CHAMFER", 1#, 1#, 1#, 0) 'Insert ply with chamfer
        Call ChangeProp(BlockRefObj, "Distance1", ply_width_x)
        
        pt12(0) = pt12(0) - ply_thk - chamf_thk: pt12(1) = pt12(1) + ply_width_y + ply_thk - chamf_thk - 1.5
        Set BlockRefObj = ThisDrawing.ModelSpace.InsertBlock(pt12, "VBA_PLY_WITH_CHAMFER", 1#, 1#, 1#, -pi / 2) 'Insert ply with chamfer
        Call ChangeProp(BlockRefObj, "Distance1", ply_width_y)
        
        pt12(0) = pt12(0) + ply_thk - chamf_thk + ply_width_x - 1.5: pt12(1) = pt12(1) + ply_thk + chamf_thk
        Set BlockRefObj = ThisDrawing.ModelSpace.InsertBlock(pt12, "VBA_PLY_WITH_CHAMFER", 1#, 1#, 1#, pi) 'Insert ply with chamfer
        Call ChangeProp(BlockRefObj, "Distance1", ply_width_x)
        
        pt12(0) = pt12(0) + ply_thk + chamf_thk: pt12(1) = pt12(1) - ply_thk + chamf_thk - ply_width_y + 1.5
        Set BlockRefObj = ThisDrawing.ModelSpace.InsertBlock(pt12, "VBA_PLY_WITH_CHAMFER", 1#, 1#, 1#, pi / 2) 'Insert ply with chamfer
        Call ChangeProp(BlockRefObj, "Distance1", ply_width_y)

        
        ' "Top clamps" ply & chamfer
        pt12(0) = pt12(0) - ply_width_x + 1.5: pt12(1) = pt12(1) + 82
        Set BlockRefObj = ThisDrawing.ModelSpace.InsertBlock(pt12, "VBA_PLY_WITH_CHAMFER", 1#, 1#, 1#, 0) 'Insert ply with chamfer
        Call ChangeProp(BlockRefObj, "Distance1", ply_width_x)

        pt12(0) = pt12(0) - ply_thk - chamf_thk: pt12(1) = pt12(1) + ply_width_y - 1.5
        Set BlockRefObj = ThisDrawing.ModelSpace.InsertBlock(pt12, "VBA_PLY_WITH_CHAMFER", 1#, 1#, 1#, -pi / 2) 'Insert ply with chamfer
        Call ChangeProp(BlockRefObj, "Distance1", ply_width_y)

        pt12(0) = pt12(0) + ply_width_x - 1.5: pt12(1) = pt12(1) + ply_thk + chamf_thk
        Set BlockRefObj = ThisDrawing.ModelSpace.InsertBlock(pt12, "VBA_PLY_WITH_CHAMFER", 1#, 1#, 1#, pi) 'Insert ply with chamfer
        Call ChangeProp(BlockRefObj, "Distance1", ply_width_x)

        pt12(0) = pt12(0) + ply_thk + chamf_thk: pt12(1) = pt12(1) - ply_width_y + 1.5
        'on error Resume Next
        If window = True Then
            ThisDrawing.ActiveLinetype = ThisDrawing.Linetypes.Item("HIDDEN")
        End If
        Set BlockRefObj = ThisDrawing.ModelSpace.InsertBlock(pt12, "VBA_PLY_WITH_CHAMFER", 1#, 1#, 1#, pi / 2) 'Insert ply with chamfer
        Call ChangeProp(BlockRefObj, "Distance1", ply_width_y)
        ThisDrawing.ActiveLinetype = ThisDrawing.Linetypes.Item("ByLayer")
        'on error GoTo ErrorHandler
        
    'Draw studs
        ' "Clamps" studs
        pt14(1) = pt13(1) - ply_thk - 1.5
        For i = 1 To n_studs_x - 1 'leave off corner stud on A side
            pt14(0) = pt13(0) - x + stud_spacing_x(i)
            Set BlockRefObj = ThisDrawing.ModelSpace.InsertBlock(pt14, stud_block_spax, 1#, 1#, 1#, 0) 'Insert bottom studs
        Next i
        pt14(0) = pt13(0) - x + stud_spacing_x(UBound(stud_spacing_x))
        Set BlockRefObj = ThisDrawing.ModelSpace.InsertBlock(pt14, stud_block_bolt, 1#, 1#, 1#, 0) 'Insert stud (corner bolt)
            
        pt14(0) = pt13(0) - x - ply_thk - 1.5
        For i = 1 To n_studs_y
            pt14(1) = pt13(1) + y - stud_spacing_y(i)
            Set BlockRefObj = ThisDrawing.ModelSpace.InsertBlock(pt14, stud_block_spax, 1#, 1#, 1#, -pi / 2) 'Insert left studs
        Next i
        
        pt14(1) = pt13(1) + y + ply_thk + 1.5
        For i = 1 To n_studs_x
            pt14(0) = pt13(0) - stud_spacing_x(i)
            Set BlockRefObj = ThisDrawing.ModelSpace.InsertBlock(pt14, stud_block_spax, 1#, 1#, 1#, pi) 'Insert top studs
        Next i
        
        pt14(0) = pt13(0) + ply_thk + 1.5
        For i = 2 To n_studs_y 'leave off corner stud on B side
            pt14(1) = pt13(1) + stud_spacing_y(i)
            Set BlockRefObj = ThisDrawing.ModelSpace.InsertBlock(pt14, stud_block_spax, 1#, 1#, 1#, pi / 2) 'Insert right studs
        Next i
        pt14(1) = pt13(1) + stud_spacing_x(1)
        Set BlockRefObj = ThisDrawing.ModelSpace.InsertBlock(pt14, stud_block_bolt, 1#, 1#, 1#, pi / 2) 'Insert stud (corner bolt)
        
        ' "Top clamps" studs
        pt13(1) = pt13(1) + 83.5 'move plan view point up for top clamps
        pt14(1) = pt13(1) - ply_thk - 1.5
        For i = 1 To n_studs_x
            pt14(0) = pt13(0) - x + stud_spacing_x(i)
            Set BlockRefObj = ThisDrawing.ModelSpace.InsertBlock(pt14, stud_block_bolt, 1#, 1#, 1#, 0) 'Insert bottom studs
        Next i
        
        pt14(0) = pt13(0) - x - ply_thk - 1.5
        For i = 1 To n_studs_y
            pt14(1) = pt13(1) + ply_width_y - stud_spacing_y(i) - 1.5
            Set BlockRefObj = ThisDrawing.ModelSpace.InsertBlock(pt14, stud_block_bolt, 1#, 1#, 1#, -pi / 2) 'Insert left studs
        Next i
        
        pt14(1) = pt13(1) + y + ply_thk + 1.5
        For i = 1 To n_studs_x
            pt14(0) = pt13(0) - stud_spacing_x(i)
            Set BlockRefObj = ThisDrawing.ModelSpace.InsertBlock(pt14, stud_block_bolt, 1#, 1#, 1#, pi) 'Insert top studs
        Next i
        
        'Switch to hidden style stud blocks
        If window = True Then stud_block_bolt = stud_block_bolt_hidden
        pt14(0) = pt13(0) + ply_thk + 1.5
        For i = 1 To n_studs_y
            pt14(1) = pt13(1) + stud_spacing_y(i)
            Set BlockRefObj = ThisDrawing.ModelSpace.InsertBlock(pt14, stud_block_bolt, 1#, 1#, 1#, pi / 2) 'Insert right studs
        Next i
        'Return to solid stud blocks
        stud_block_bolt = Replace(CStr(stud_block_bolt), "_HIDDEN", "")

        'Draw studs on turned out window clamp (right, y)
        If window = True Then
            For i = 1 To n_studs_y
                pt5(0) = pt13(0) + ply_thk + 1.5 + 1 + Sin(swing_ang) + (3.25 + y - stud_spacing_y(i)) * Cos(swing_ang):  pt5(1) = pt13(1) + y + ply_thk + 2.5 - Cos(swing_ang) + (3.25 + y - stud_spacing_y(i)) * Sin(swing_ang)
                Set BlockRefObj = ThisDrawing.ModelSpace.InsertBlock(pt5, stud_block_bolt, 1#, 1#, 1#, swing_ang + pi) 'Insert right studs
                pt5(0) = pt13(0) + ply_thk + 1.5 + 1 + 2.5 * Sin(swing_ang) + (3.25 + y - chamf_thk) * Cos(swing_ang):   pt5(1) = pt13(1) + y + ply_thk + 2.5 - 2.5 * Cos(swing_ang) + (3.25 + y - chamf_thk) * Sin(swing_ang)
                Set BlockRefObj = ThisDrawing.ModelSpace.InsertBlock(pt5, "VBA_PLY_WITH_CHAMFER", 1#, 1#, 1#, swing_ang + pi) 'Insert plywood
                Call ChangeProp(BlockRefObj, "Distance1", ply_width_y)
            Next i
        End If
        
    'Draw brace clamps
    
    'Draw brace clamps in "CLAMPS" plan view if attached to clamp, otherwise stay at top clamps
    If brace_clamp > n_top_clamps Then
        pt13(1) = pt13(1) - 83.5
    End If
    
    'The 3 clamp locations are: (1) upper left stud on the x side
    '                           (2) upper right stud OR clamp tail on the x side
    '                           (3) lower left stud on the y side
    
    If clamp_L - 12.5 - x >= 8.5 Then 'if clamp "tail" is long enough, place this brace on tail
        pt16(0) = pt13(0) - x - 6.25 + clamp_L - 4.25: pt16(1) = pt13(1) + ply_thk + y
        Set BlockRefObj = ThisDrawing.ModelSpace.InsertBlock(pt16, "VBA_AFB_PLAN", 1#, 1#, 1#, 0)
    Else
        If Round(stud_spacing_x(2) - stud_spacing_x(1) - 3.5, 3) >= min_stud_gap Then 'Otherwise check if there is room to place AFB by upper right stud
            pt16(0) = pt13(0) - stud_spacing_x(1) - 3.5 - (stud_spacing_x(2) - stud_spacing_x(1) - 3.5) / 2: pt16(1) = pt13(1) + ply_thk + y
            Set BlockRefObj = ThisDrawing.ModelSpace.InsertBlock(pt16, "VBA_AFB_PLAN", 1#, 1#, 1#, 0)
        Else 'If no room on far stud, force it onto the clamp tail anyways with some offset
            pt16(0) = pt13(0) - x - 6.25 + clamp_L - 2: pt16(1) = pt13(1) + ply_thk + y
            Set BlockRefObj = ThisDrawing.ModelSpace.InsertBlock(pt16, "VBA_AFB_PLAN", 1#, 1#, 1#, 0)
        End If
    End If
    
    pt16(0) = pt13(0) - x + 3.8125:     pt16(1) = pt13(1) + ply_thk + y
    Set BlockRefObj = ThisDrawing.ModelSpace.InsertBlock(pt16, "VBA_AFB_PLAN", 1#, 1#, 1#, 0) 'Insert AFB by upper left x stud

    pt16(0) = pt13(0) - x - ply_thk:    pt16(1) = pt13(1) + 3.8125
    Set BlockRefObj = ThisDrawing.ModelSpace.InsertBlock(pt16, "VBA_AFB_PLAN", 1#, 1#, 1#, pi / 2) 'Insert AFB by lower left y stud

    'Add plan note 9 for AFB
    pt16(0) = pt13(0) - x: pt16(1) = pt13(1)
    If y > 27 Then
        Set BlockRefObj = ThisDrawing.ModelSpace.InsertBlock(pt16, "VBA_PLAN_NOTES9A", 1#, 1#, 1#, 0)
    Else
        pt16(1) = pt13(1) + y
        Set BlockRefObj = ThisDrawing.ModelSpace.InsertBlock(pt16, "VBA_PLAN_NOTES9B", 1#, 1#, 1#, 0)
    End If
    
    'Fix location for the rest of plan view drawing if the AFBs were drawn in the "TOP CLAMPS" plan view
    If brace_clamp <= n_top_clamps Then
        pt13(1) = pt13(1) - 83.5
    End If

    ThisDrawing.ActiveLayer = ThisDrawing.Layers("CONC")
    Dim hatchObj As AcadHatch
    Dim OuterLoop(0) As AcadEntity
    Dim pl_pts(0 To 9) As Double
    
    'Set boundry of hatch (must close hatch by returning to initial point)
    pl_pts(0) = pt13(0):     pl_pts(1) = pt13(1)
    pl_pts(2) = pt13(0) - x: pl_pts(3) = pt13(1)
    pl_pts(4) = pt13(0) - x: pl_pts(5) = pt13(1) + y
    pl_pts(6) = pt13(0):     pl_pts(7) = pt13(1) + y
    pl_pts(8) = pt13(0):     pl_pts(9) = pt13(1)
    
    Set OuterLoop(0) = ThisDrawing.ModelSpace.AddLightWeightPolyline(pl_pts) 'Assign the pline object as the hatch's outer loop (inner loop optional and skipped here)
    Set hatchObj = ThisDrawing.ModelSpace.AddHatch(0, "AR-CONC", True) 'Set hatch
    hatchObj.AppendOuterLoop (OuterLoop)
    OuterLoop(0).Delete
    
    pl_pts(1) = pl_pts(1) + 83.5: pl_pts(3) = pl_pts(3) + 83.5: pl_pts(5) = pl_pts(5) + 83.5: pl_pts(7) = pl_pts(7) + 83.5: pl_pts(9) = pl_pts(9) + 83.5 'Move pts to top clamps' plan
    Set OuterLoop(0) = ThisDrawing.ModelSpace.AddLightWeightPolyline(pl_pts)
    Set hatchObj = ThisDrawing.ModelSpace.AddHatch(0, "AR-CONC", True)
    hatchObj.AppendOuterLoop (OuterLoop)
    OuterLoop(0).Delete
    
    'Draw text in plan views
    ThisDrawing.ActiveLayer = ThisDrawing.Layers("FORM")
    
    'Shrink text for small columns
    If x <= 16 Or y <= 16 Then
        pt17(0) = pt13(0) - x: pt17(1) = pt13(1) + 0.75 + y / 2
        Set MTextObject2 = ThisDrawing.ModelSpace.AddMText(pt17, x, "CLAMPS")
        MTextObject2.StyleName = "Arial Narrow Bold": MTextObject2.Height = 1.5: MTextObject2.AttachmentPoint = acAttachmentPointTopCenter
    
        pt17(0) = pt13(0) - x: pt17(1) = pt13(1) + 2.1 + y / 2 + 83.5
        Set MTextObject2 = ThisDrawing.ModelSpace.AddMText(pt17, x, "TOP" & vbNewLine & "CLAMPS")
        MTextObject2.StyleName = "Arial Narrow Bold": MTextObject2.Height = 1.5: MTextObject2.AttachmentPoint = acAttachmentPointTopCenter
    Else
        pt17(0) = pt13(0) - x: pt17(1) = pt13(1) + 1.25 + y / 2
        Set MTextObject2 = ThisDrawing.ModelSpace.AddMText(pt17, x, "CLAMPS")
        MTextObject2.StyleName = "Arial Narrow Bold": MTextObject2.Height = 2.5: MTextObject2.AttachmentPoint = acAttachmentPointTopCenter
    
        pt17(0) = pt13(0) - x: pt17(1) = pt13(1) + 3.35 + y / 2 + 83.5
        Set MTextObject2 = ThisDrawing.ModelSpace.AddMText(pt17, x, "TOP" & vbNewLine & "CLAMPS")
        MTextObject2.StyleName = "Arial Narrow Bold": MTextObject2.Height = 2.5: MTextObject2.AttachmentPoint = acAttachmentPointTopCenter
    End If
        
    For i = 0 To 1
        pt17(0) = pt13(0) - x: pt17(1) = pt13(1) + y - 0.5 + 83.5 * i
        Set MTextObject1 = ThisDrawing.ModelSpace.AddMText(pt17, x, "SIDE A")
        MTextObject1.StyleName = "Arial Narrow": MTextObject1.AttachmentPoint = acAttachmentPointTopCenter: MTextObject1.Height = 1.75
        
        If DrawB = True Then
            pt17(0) = pt13(0) - x + 0.5: pt17(1) = pt13(1) + 83.5 * i
            Set MTextObject1 = ThisDrawing.ModelSpace.AddMText(pt17, y, "SIDE B")
            MTextObject1.StyleName = "Arial Narrow": MTextObject1.Rotation = pi / 2: MTextObject1.AttachmentPoint = acAttachmentPointTopCenter: MTextObject1.Height = 1.75
        End If
        
        pt17(0) = pt13(0) - x: pt17(1) = pt13(1) + 2.25 + 83.5 * i
        Set MTextObject1 = ThisDrawing.ModelSpace.AddMText(pt17, x, x)
        MTextObject1.StyleName = "Arial Narrow": MTextObject1.AttachmentPoint = acAttachmentPointTopCenter: MTextObject1.Height = 1.75
        
        pt17(0) = pt13(0) - 2.25: pt17(1) = pt13(1) + 83.5 * i
        Set MTextObject1 = ThisDrawing.ModelSpace.AddMText(pt17, y, y)
        MTextObject1.StyleName = "Arial Narrow": MTextObject1.Rotation = pi / 2: MTextObject1.AttachmentPoint = acAttachmentPointTopCenter: MTextObject1.Height = 1.75
    Next i
    
    'Add all static lines, text, objects, and images as one block
    'For tall columns use the "high" background to accomdate the column size
    'For smaller columns use the "medium" background to avoid the unaesthetic blank space between a relatively short column and the top of page details
    If z > 190 Then
        Set BlockRefObj = ThisDrawing.ModelSpace.InsertBlock(pt_o, "VBA_COLUMN_BACKGROUND_HIGH", 1#, 1#, 1#, 0)
    Else
        Set BlockRefObj = ThisDrawing.ModelSpace.InsertBlock(pt_o, "VBA_COLUMN_BACKGROUND_MEDIUM", 1#, 1#, 1#, 0)
    End If
    
    'Add alternative picking eye deatils if no window is used
    If window = False Then
        pt_blk(0) = pt_o(0) + 402: pt_blk(1) = pt_o(1) + 261 - 36 * Abs(z <= 190)
        Set BlockRefObj = ThisDrawing.ModelSpace.InsertBlock(pt_blk, "VBA_COLUMN_ALT_PICKING_DETAILS", 1#, 1#, 1#, 0)
    End If
    
    'Add detail references to each elevation view
    ThisDrawing.ActiveLayer = ThisDrawing.Layers("FORM")
    
    'Side A detail reference
    pt_blk(0) = ptA(0) + ply_width_x / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "A"
        End If
        If AttList(i).TextString = "DESCRIPTION" Then
            AttList(i).TextString = "SIDE ""A"" PANEL"
        End If
        If AttList(i).TextString = "REFERENCE" Then
            AttList(i).TextString = "VIEWED FROM PLYWOOD FACE"
        End If
    Next i
    
    'Side B detail reference
    If DrawB = True Then
        pt_blk(0) = ptB(0) + ply_width_y / 2: pt_blk(1) = pt_o(1) + 9
        Set BlockRefObj = ThisDrawing.ModelSpace.InsertBlock(pt_blk, "VBA_DETAIL_REF", 0.75, 0.75, 0.75, 0)
        AttList = BlockRefObj.GetAttributes
        For i = LBound(AttList) To UBound(AttList) 'Assign attribute values
            If AttList(i).TextString = "X" Then
                AttList(i).TextString = "B"
            End If
            If AttList(i).TextString = "DESCRIPTION" Then
                AttList(i).TextString = "SIDE ""B"" PANEL"
            End If
            If AttList(i).TextString = "REFERENCE" Then
                AttList(i).TextString = "VIEWED FROM PLYWOOD FACE"
            End If
        Next i
    End If

    'Window detail reference
    If DrawW = True Then
        pt_blk(0) = ptW(0) + ply_width_w / 2: pt_blk(1) = pt_o(1) + 9
        Set BlockRefObj = ThisDrawing.ModelSpace.InsertBlock(pt_blk, "VBA_DETAIL_REF", 0.75, 0.75, 0.75, 0)
        AttList = BlockRefObj.GetAttributes
        For i = LBound(AttList) To UBound(AttList) 'Assign attribute values
            If AttList(i).TextString = "X" Then
                AttList(i).TextString = "W"
            End If
            If AttList(i).TextString = "DESCRIPTION" Then
                AttList(i).TextString = "POUR WINDOW PANEL"
            End If
            If AttList(i).TextString = "REFERENCE" Then
                AttList(i).TextString = "VIEWED FROM PLYWOOD FACE"
            End If
        Next i
    End If
    
    'Elevation view detail reference
    pt_blk(0) = ptE(0) + ply_width_e / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "E"
        End If
        If AttList(i).TextString = "DESCRIPTION" Then
            AttList(i).TextString = "COLUMN FORM ELEVATION"
        End If
        If AttList(i).TextString = "REFERENCE" Then
            AttList(i).TextString = ""
        End If
    Next i
    
    'Add lower left fab count below "column form elevation"
    ThisDrawing.ActiveLayer = ThisDrawing.Layers("FORM")
    count_str = "FAB " & n_col & "-EA"
    pt32(0) = ptE(0) + ply_width_e / 2: pt32(1) = pt_o(1) + 7
    Set MTextObject2 = ThisDrawing.ModelSpace.AddMText(pt32, 30, count_str)
    MTextObject2.Height = 2.5
    
    
'#####################################################################################
'                                S H E E T I N G
'#####################################################################################
   
    Dim ptVP1(0 To 2) As Double
    Dim ptVP2(0 To 2) As Double
    Dim pt35(0 To 2) As Double
    Dim AreaName As String
    Dim oprop As AcadDynamicBlockReferenceProperty
    
    'Insert the McClone area block
    AreaName = CStr(AreaBox.Value)
    pt35(0) = pt_o(0) + 548.37926872: pt35(1) = pt_o(1) + 186: pt35(2) = 0
    Set BlockRefObj = ThisDrawing.ModelSpace.InsertBlock(pt35, "VBA_OFFICE_LOCATION", (2 / 3), (2 / 3), (2 / 3), 0)
    
    Props = BlockRefObj.GetDynamicBlockProperties
    For i = LBound(Props) To UBound(Props)
        Set oprop = Props(i) 'Get object properties from border block
        If oprop.PropertyName = "Visibility1" Then 'Finds visibility state property
            oprop.Value = AreaBox.Value
        End If
    Next i
    
    'Insert border
    Set BlockRefObj = ThisDrawing.ModelSpace.InsertBlock(pt_click, "VBA_24X36_LAYOUT", 1#, 1#, 1#, 0) 'Insert 3/4" = 1'-0" sheet boundry
    BlockRefObj.ScaleEntity pt_click, 12 / 0.75
    
    'Sets Sheet issued for: "" text (defined as a block reference property)
    Props = BlockRefObj.GetDynamicBlockProperties
    For i = LBound(Props) To UBound(Props)
        Set oprop = Props(i) 'Get object properties from border block
        If oprop.PropertyName = "Visibility1" Then 'Finds visibility state property
            oprop.Value = SheetIssuedForBox.Value
        End If
    Next i
    
    'Place timestamp in lower left corner, outside of sheet boundry
    pt34(0) = pt_o(0) - 1.65: pt34(1) = pt_o(1): pt34(2) = pt_o(2)
    ThisDrawing.ActiveTextStyle = ThisDrawing.TextStyles("VBA_txt_narrow")
    Set MTextObject2 = ThisDrawing.ModelSpace.AddMText(pt34, 18, Now())
    MTextObject2.Height = 1.25
    MTextObject2.Rotate pt34, pi / 2
    
    'Places other text (defined as attributes)
    AttList = BlockRefObj.GetAttributes
    For i = LBound(AttList) To UBound(AttList)
        ' Check for the correct attribute tag.
        If AttList(i).TextString = "SHEET NAME" Then
            AttList(i).TextString = "" & ProjectNameBox.Value
        End If
        If AttList(i).TextString = "PROJECT TITLE" Then
            AttList(i).TextString = "" & ProjectTitleBox.Value
        End If
        If AttList(i).TextString = "PROJECT ADDRESS" Then
            AttList(i).TextString = "" & ProjectAddressBox.Value
        End If
        If AttList(i).TextString = "DATE" Then
            AttList(i).TextString = "" & DateBox.Value
        End If
        If AttList(i).TextString = "SCALE" Then
            AttList(i).TextString = "3/4'' = 1'-0''"
        End If
        If AttList(i).TextString = "DRAWN BY" Then
            AttList(i).TextString = "" & DrawnByBox.Value
        End If
        If AttList(i).TextString = "JOB NUMBER" Then
            AttList(i).TextString = "" & JobNoBox.Value
        End If
        If AttList(i).TextString = "SHEET_#" Then
            AttList(i).TextString = "" & SheetBox.Value
        End If
        If AttList(i).TextString = "SUFFIX" Then
            AttList(i).TextString = "" & SuffixBox.Value
        End If
    Next i

    'Create a layout sheet for printing
    If 1 = 2 Then
    ' ======== The Layout ========
        Dim strLayoutName As String
        Dim strLayoutNameOriginal As String
        Dim strPaperSize As String
        Dim objLayout As AcadLayout
        Dim intLayoutCount As Integer: intLayoutCount = 0 'A counter for views with duplicate names (e.g. 24x24 COL, 24x24 COL (1), 24x24 COL (2))
    
        'Name the layout
        strLayoutName = "test"
        strLayoutNameOriginal = strLayoutName
        
        'Use a different layout name if the name already exists
RetryCreatingLayout:
        For i = 0 To ThisDrawing.Layouts.Count - 1
            If ThisDrawing.Layouts.Item(i).Name = strLayoutName Then
                intLayoutCount = intLayoutCount + 1
                strLayoutName = strLayoutNameOriginal & " (" & intLayoutCount & ")"
                GoTo RetryCreatingLayout
            End If
        Next i
        
        'Create a new layout
        Set objLayout = ThisDrawing.Layouts.Add(strLayoutName)
        
        'Make the new layout active and activate paperspace
        ThisDrawing.ActiveLayout = objLayout
        ThisDrawing.ActiveSpace = acPaperSpace
    
        'Allow editing of the model from floating paper space viewports.
        ThisDrawing.MSpace = True
        
        'Apply a paper size to the layout
        'strPaperSize = "ARCH full bleed D (36.00 x 24.00 Inches)"
        'objLayout.CanonicalMediaName = strPaperSize
        
        
        Dim varPaperSizeNames As Variant
        Dim fdsa As String
        
        varPaperSizeNames = objLayout.GetCanonicalMediaNames()
        For i = LBound(varPaperSizeNames) To UBound(varPaperSizeNames)
            fdsa = fdsa & varPaperSizeNames(i) & vbNewLine
        Next i
        MsgBox fdsa
        
        
    ' ======== The Plot Configuration ========
        Dim objPlotConfig As AcadPlotConfiguration
        
        
        
    ' ======== The View ========
        Dim objView As AcadView
        Dim strViewName As String
        Dim strViewNameOriginal As String
        Dim intViewCount As Integer: intViewCount = 0
        Dim viewCenter(0 To 1) As Double 'Center point of view
        Dim viewHeight As Double
        Dim viewWidth As Double
        Dim teststr As String
        
        'Name the view
        strViewName = "preview"
        strViewNameOriginal = strViewName
        
        'Use a different view name if the name already exists
RetryCreatingView:
        For i = 0 To ThisDrawing.Views.Count - 1
            If ThisDrawing.Views.Item(i).Name = strViewName Then
                
                intViewCount = intViewCount + 1
                strViewName = strViewNameOriginal & " (" & intViewCount & ")"
                GoTo RetryCreatingView
            End If
        Next i
        
        'Create the view
        Set objView = ThisDrawing.Views.Add(strViewName)
        
        'Size the view
        viewCenter(0) = 431.0183228: viewCenter(1) = 287.27197305
        viewHeight = 580.21968823
        viewWidth = 871.37818075
        
        With objView
            .Center = viewCenter
            .Height = viewHeight
            .Width = viewWidth
        End With
        
        'Display list of views that exist
        If ThisDrawing.Views.Count > 0 Then
            For Each objView In ThisDrawing.Views
                teststr = teststr & objView.Name & vbCrLf
            Next
        Else
            MsgBox "no views!"
        End If
        'msgBox teststr
        
    ' ======== The Viewport ========
        Dim strPSViewPortName As String 'Paperspace viewport name
        Dim objPSViewPort As AcadPViewport 'Paperspace viewport object
        Dim ptPSVP(0 To 2) As Double 'Center point of paperspace viewport
        Dim objAcadObject As AcadObject
        
        'Delete existing viewports
        'For Each objAcadObject In ThisDrawing.PaperSpace
        '    MsgBox TypeName(objAcadObj)
        '    If TypeName(objAcadObj) = "IAcadPViewport" Then
        '        objAcadObject.Delete
        '    End If
        'Next
        
        'Delete existing viewports
        For Each objPSViewPort In ThisDrawing.PaperSpace
            objPSViewPort.Delete
        Next
        
        'Define centerpoint of paperspace viewport
        ptPSVP(0) = 17.875: ptPSVP(1) = 11.875: ptPSVP(2) = 0
        
        'Name the viewport
        strPSViewPortName = "Hello3"
    
        'Create a new viewport
        Set objPSViewPort = ThisDrawing.PaperSpace.AddPViewport(ptPSVP, 36, 24)

        'Make the viewport active
        objPSViewPort.Display acOn
        ThisDrawing.MSpace = True 'This gets turned off at some point? Turn it back on here.
        ThisDrawing.ActivePViewport = objPSViewPort
        
        'Use a custom scale
        objPSViewPort.StandardScale = acVpCustomScale
        objPSViewPort.CustomScale = 0.04136364
        
        'Apply the view to the viewport
        'ThisDrawing.SendCommand "-view" & vbCr & "R" & vbCr & strViewName & vbCr
        'objPSViewPort.SetView = objView
        
        ' Make sure the Viewport is displayed and on
        'objPSViewPort.Display (True)
        'objPSViewPort.ViewportOn = True
     
        ' Before making a pViewport active the mspace property needs
        ' to be True for a floating viewport
        'ThisDrawing.ActivePViewport = objPSViewPort
        'ThisDrawing.Regen (acActiveViewport)
    End If
    
last_line:

'#####################################################################################
'                   M I S C E L L A N E O U S  &  C L E A N  U P
'#####################################################################################

    'If custom clamp size is selected but too small, warn the user
    If ClampSizeButton1.Value = True Then
        If x > 24 Or y > 24 Then
            MsgBox ("Warning: Selected clamp appears too small for this column")
        End If
    ElseIf ClampSizeButton2.Value = True Then
        If x > 36 Or y > 36 Then
            MsgBox ("Warning: Selected clamp appears too small for this column")
        End If
    ElseIf ClampSizeButton3.Value = True Then
        If x > 48 Or y > 48 Then
            MsgBox ("Warning: Selected clamp appears too small for this column")
        End If
    End If
    
    'Restore locked and frozen layers
    For i = 1 To UBound(UsedLayerList)
        If LockedLayerList(i) = 1 Then
            Set LayerObj = ThisDrawing.Layers(UsedLayerList(i))
            LayerObj.Lock = True
        End If
        If FrozenLayerList(i) = 1 Then
            Set LayerObj = ThisDrawing.Layers(UsedLayerList(i))
            LayerObj.Freeze = True
            MsgBox ("Warning: The " & UsedLayerList(i) & " layer is not visible because it is frozen")
        End If
        If InvisLayerList(i) = 1 Then
            MsgBox ("Warning: The " & UsedLayerList(i) & " layer is not visible because it is turned off")
        End If
    Next i
    
    ThisDrawing.ActiveDimStyle = OldDimStyle
    ThisDrawing.ActiveTextStyle = OldTextStyle
    ThisDrawing.ActiveLayer = OldLayer
    
    'Clean up objects that may be causing a lock violation
    Set MTextObject1 = Nothing
    Set MTextObject2 = Nothing
    Set objTextStyle = Nothing
    Set dimObj = Nothing
    Set LineObj = Nothing
    Set plineObj = Nothing
    Set BlockRefObj = Nothing
    Set ObjDynBlockProp = Nothing
    Set OldDimStyle = Nothing
    Set OldTextStyle = Nothing
    Set OldLayer = Nothing
    Set NewDimStyle = Nothing
    Set NewTextStyle = Nothing
    Set NewLayer = Nothing
    
    GoTo SkipErrorHandler
ErrorHandler:
    If Err.Number = -2147352567 Then 'This error occurs when the user presses the ESC key while inside the GetPoint utility
        ColumnCreator.show
        Exit Sub
    ElseIf Err.Number = -2145386422 Then 'This error occurs when the path to Egnyte isn't found
        MsgBox ("Error: VBA block library not found at: " & FileToInsert & vbNewLine & vbNewLine & "Check Egnyte (Z:\) connection. Try closing and relaunching Egnyte Connect.")
        Exit Sub
    ElseIf Err.Number = -2145386445 Then 'This error occurs when a block definition that doesn't exist is attempted to be inserted.
        If BlockExists = True Then
            MsgBox ("This drawing seems to be missing blocks for this VBA script. This is normal if you are using new button features on an old drawing. The block library will be re-downloaded and this script terminated." & vbNewLine & vbNewLine & "Please run the button again.")
            'Insert the block library then delete it
            FileToInsert = FileLocationPrefix & "VBA_Block_Library.dwg"
            Set BlockDwg = ThisDrawing.ModelSpace.InsertBlock(insertionPnt, FileToInsert, 1#, 1#, 1#, 0)
            BlockDwg.Delete
            Exit Sub
        Else
            MsgBox ("Error: This drawing seems to be missing blocks for this VBA script despite the block library having been downloaded. The library may be missing the necessary blocks, or something mysterious has gone horribly wrong." & vbNewLine & vbNewLine & "Library location: " & FileToInsert)
            Exit Sub
        End If
    Else 'Generic error message
        MsgBox ("An error occured." & vbNewLine & "error " & Err.Number & vbNewLine & Err.Description)
        Exit Sub
    End If
    
SkipErrorHandler:

End Sub



Public Function Dec2Frac(ByVal dFraction As Double) As String
    
    'Type: Public Function
    'Name: Decimal to Fraction Converter
    'Purpose: Converts a passed decimal to a fraction
    'Limitations: Will not convert to mixed fractions
    'Author: Unknown
    'Arguments: dFraction is the decimal to convert
    'Return Value: String representingthe fraction
    'Useage: Dec2Frac(.125)
    'Notes:
    
    Dim df As Double
    Dim lUpperPart As Long
    Dim lLowerPart As Long
    
    lUpperPart = 1
    lLowerPart = 1
    
    df = lUpperPart / lLowerPart
    
    While (df <> dFraction)
    If (df < dFraction) Then
    lUpperPart = lUpperPart + 1
    Else
    lLowerPart = lLowerPart + 1
    lUpperPart = dFraction * lLowerPart
    End If
    df = lUpperPart / lLowerPart
    Wend
    
    Dec2Frac = CStr(lUpperPart) & "/" & CStr(lLowerPart)

End Function
Public Function ChangeProp(BlockRefObj, PropName, PropValue)

    Props = BlockRefObj.GetDynamicBlockProperties
    Dim oprop As AcadDynamicBlockReferenceProperty
    
    For i = LBound(Props) To UBound(Props)
        Set oprop = Props(i) 'Get object properties from block one at a time
        If oprop.PropertyName = PropName Then 'compare to property name
            oprop.Value = PropValue 'if name matches, assign new PropValue
        End If
    'Exit For
    Next i
End Function
Public Function DrawDim(x1 As Double, y1 As Double, x2 As Double, y2 As Double, x3 As Double, y3 As Double)

    Dim dimObj As AcadDimAligned
    Dim point1(0 To 2) As Double 'first point
    Dim point2(0 To 2) As Double 'second point
    Dim location(0 To 2) As Double 'text location
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimAligned(point1, point2, location)
End Function
Public Function DrawDimSuffix(x1 As Double, y1 As Double, x2 As Double, y2 As Double, x3 As Double, y3 As Double, txt As String)

    Dim dimObj As AcadDimAligned
    Dim point1(0 To 2) As Double
    Dim point2(0 To 2) As Double
    Dim location(0 To 2) As Double
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimAligned(point1, point2, location)
    dimObj.TextSuffix = txt
    
End Function
Public Function DrawDimLin(x1 As Double, y1 As Double, x2 As Double, y2 As Double, x3 As Double, y3 As Double, angle As Double)

    Dim dimObj As AcadDimRotated
    Dim point1(0 To 2) As Double 'first point
    Dim point2(0 To 2) As Double 'second point
    Dim location(0 To 2) As Double 'text location
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimRotated(point1, point2, location, angle)
End Function
Public Function DrawDimLinSuffixLeader(x1 As Double, y1 As Double, x2 As Double, y2 As Double, x3 As Double, y3 As Double, x4 As Double, y4 As Double, txt As String, angle As Double)

    Dim dimObj As AcadDimRotated
    Dim point1(0 To 2) As Double
    Dim point2(0 To 2) As Double
    Dim location(0 To 2) As Double
    Dim txtLocation(0 To 2) As Double
    
    ' Define the dimension
    point1(0) = x1#: point1(1) = y1#: point1(2) = 0#
    point2(0) = x2#: point2(1) = y2#: point2(2) = 0#
    location(0) = x3#: location(1) = y3#: location(2) = 0#
    txtLocation(0) = x4#: txtLocation(1) = y4#: txtLocation(2) = 0#
    
    ' Create an aligned dimension object in model space
    Set dimObj = ThisDrawing.ModelSpace.AddDimRotated(point1, point2, location, angle)
    dimObj.TextMovement = acMoveTextAddLeader
    dimObj.TextPosition = txtLocation
    dimObj.TextSuffix = txt
End Function
Public Function DrawDimLinLeader(x1 As Double, y1 As Double, x2 As Double, y2 As Double, x3 As Double, y3 As Double, x4 As Double, y4 As Double, angle As Double)

    Dim dimObj As AcadDimRotated
    Dim point1(0 To 2) As Double
    Dim point2(0 To 2) As Double
    Dim location(0 To 2) As Double
    Dim txtLocation(0 To 2) As Double
    
    ' Define the dimension
    point1(0) = x1#: point1(1) = y1#: point1(2) = 0#
    point2(0) = x2#: point2(1) = y2#: point2(2) = 0#
    location(0) = x3#: location(1) = y3#: location(2) = 0#
    txtLocation(0) = x4#: txtLocation(1) = y4#: txtLocation(2) = 0#
    
    ' Create an aligned dimension object in model space
    Set dimObj = ThisDrawing.ModelSpace.AddDimRotated(point1, point2, location, angle)
    dimObj.TextMovement = acMoveTextAddLeader
    dimObj.TextPosition = txtLocation
End Function
'draws a rectangle with lower left corner at xoff, yoff with COORDINATES for far point specified
'    4_______3B
'    |       |
'    |       |
'    |_______|
'   A1       2

    Public Function DrawRectangle(xA As Double, yA As Double, xB As Double, yB As Double)
        Dim plineObj As AcadLWPolyline
        Dim pts(0 To 7) As Double
        
        pts(0) = xA#:   pts(1) = yA
        pts(2) = xB#:   pts(3) = yA
        pts(4) = xB#:   pts(5) = yB
        pts(6) = xA#:   pts(7) = yB

        Set plineObj = ThisDrawing.ModelSpace.AddLightWeightPolyline(pts)
        plineObj.Closed = True

    End Function
Public Function FindMax(Arr As Variant)
    Dim RetMax As Double
    RetMax = Arr(LBound(Arr)) 'initialize with first value
    
    For i = LBound(Arr) To UBound(Arr)
    If Arr(i) > RetMax Then
        RetMax = Arr(i)
    End If
    Next i
    FindMax = RetMax
End Function
Public Function FindMin(Arr As Variant)
    Dim RetMin As Double
    RetMin = Arr(LBound(Arr)) 'initialize with first value
    For i = LBound(Arr) To UBound(Arr)
    If Arr(i) < RetMin Then
        RetMin = Arr(i)
    End If
    Next i
    FindMin = RetMin
End Function
Public Function RoundUp(num As Double) As Integer
    If num > Int(num) Then
    num = Int(num) + 1
    Else
    num = Int(num)
    End If
    RoundUp = num
End Function
Public Function RoundDown(num As Double) As Integer
    num = Int(num)
    RoundDown = num
End Function

Private Sub SaveButton_Click()
    Dim SheetDataFilePath As String
    Dim SheetDataFileName As String
    Dim SheetDataFilePathAndName As String
    Dim sHostName As String
    Dim fso As New FileSystemObject
    Dim oFile As Object
    
    'Set file name and path
    SheetDataFilePath = "C:\ProgramData\Autodesk\VBA Saved Files"
    SheetDataFileName = "Column Sheet Data.txt"
    SheetDataPathAndName = SheetDataFilePath & "\" & SheetDataFileName
    
    'Create folder path
    If Not FolderExists("C:\ProgramData") Then
        FolderCreate ("C:\ProgramData")
    End If
    If Not FolderExists("C:\ProgramData\Autodesk") Then
        FolderCreate ("C:\ProgramData\Autodesk")
    End If
    If Not FolderExists(SheetDataFilePath) Then
        FolderCreate (SheetDataFilePath)
    End If

    'Create a text file and write the following lines
    Set oFile = fso.CreateTextFile(SheetDataPathAndName, True) 'True allows overwriting
    
    oFile.WriteLine ProjectNameBox.Value
    oFile.WriteLine ProjectTitleBox.Value
    oFile.WriteLine ProjectAddressBox.Value
    oFile.WriteLine DateBox.Value
    oFile.WriteLine SheetIssuedForBox.Value
    oFile.WriteLine ScaleBox.Value
    oFile.WriteLine DrawnByBox.Value
    oFile.WriteLine JobNoBox.Value
    oFile.WriteLine SheetBox.Value
    oFile.WriteLine SuffixBox.Value
    oFile.WriteLine AreaBox.Value
    
    oFile.Close
    Set fso = Nothing
    Set oFile = Nothing

End Sub

Private Sub LoadButton_Click()
    Dim SheetDataFilePath As String
    Dim SheetDataFileName As String
    Dim SheetDataFilePathAndName As String
    Dim mystring As String
    Dim temp_lines(1 To 11) As String
    
    SheetDataFilePath = "C:\ProgramData\Autodesk\VBA Saved Files"
    SheetDataFileName = "Column Sheet Data.txt"
    SheetDataPathAndName = SheetDataFilePath & "\" & SheetDataFileName
    
    If Dir(SheetDataPathAndName) = "" Then
        MsgBox ("Error: You can't load a file you haven't saved")
        Exit Sub
    End If
    
    Open SheetDataPathAndName For Input As #1
    i = 1
    
    Do While Not EOF(1)
        Line Input #1, mystring
        temp_lines(i) = mystring
        i = i + 1
    Loop
    Close #1
    
    'Load the following lines to the corresponding variables
    ProjectNameBox.Value = temp_lines(1)
    ProjectTitleBox.Value = temp_lines(2)
    ProjectAddressBox.Value = temp_lines(3)
    DateBox.Value = temp_lines(4)
    SheetIssuedForBox.Value = temp_lines(5)
    ScaleBox.Value = temp_lines(6)
    DrawnByBox.Value = temp_lines(7)
    JobNoBox.Value = temp_lines(8)
    SheetBox.Value = temp_lines(9)
    SuffixBox.Value = temp_lines(10)
    AreaBox.Value = temp_lines(11)
End Sub

Private Sub SquaringCornerOptionPickingButton_Click()
    SquaringCornerOptionRegularButton.Value = False
    SquaringCornerOptionPickingButton.Value = True
End Sub
Private Sub SquaringCornerOptionRegularButton_Click()
    SquaringCornerOptionRegularButton.Value = True
    SquaringCornerOptionPickingButton.Value = False
End Sub
Private Sub SquaringCornerOptionPickingButton_KeyPress(ByVal KeyAscii As MSForms.ReturnInteger)
    If KeyAscii = 27 Then ColumnCreator.Hide
End Sub
Private Sub SquaringCornerOptionRegularButton_KeyPress(ByVal KeyAscii As MSForms.ReturnInteger)
    If KeyAscii = 27 Then ColumnCreator.Hide
End Sub
Function FolderExists(ByVal path As String) As Boolean
    FolderExists = False
    Dim fso As New FileSystemObject
    If fso.FolderExists(path) Then FolderExists = True
End Function

Function FolderCreate(ByVal path As String) As Boolean

FolderCreate = True
Dim fso As New FileSystemObject

If FolderExists(path) Then
    Exit Function
Else
    'on error GoTo DeadInTheWater
    fso.CreateFolder path ' could there be any error with this, like if the path is really screwed up?
    Exit Function
End If

DeadInTheWater:
    MsgBox "A folder could not be created for the following path: " & path & ". Check the path name and try again."
    FolderCreate = False
    Exit Function
    
End Function

Private Sub UserForm_Initialize()
    SheetIssuedForBox.AddItem "PRELIMINARY"
    SheetIssuedForBox.AddItem "SUBMITTAL REVIEW"
    SheetIssuedForBox.AddItem "FOR CONSTRUCTION"
    SheetIssuedForBox.AddItem "OTHER"
    
    AreaBox.AddItem "CO"
    AreaBox.AddItem "HI"
    AreaBox.AddItem "NCA"
    AreaBox.AddItem "SCA"
    AreaBox.AddItem "STX"
    AreaBox.AddItem "WA"
    AreaBox.Value = "NCA"
    
    sSheetIssuedForBox.AddItem "PRELIMINARY"
    sSheetIssuedForBox.AddItem "SUBMITTAL REVIEW"
    sSheetIssuedForBox.AddItem "FOR CONSTRUCTION"
    sSheetIssuedForBox.AddItem "OTHER"
    
    sAreaBox.AddItem "CO"
    sAreaBox.AddItem "HI"
    sAreaBox.AddItem "NCA"
    sAreaBox.AddItem "SCA"
    sAreaBox.AddItem "STX"
    sAreaBox.AddItem "WA"
    sAreaBox.Value = "NCA"
    
    DateBox.Value = Left(Now(), InStr(1, Now(), " ")) 'Now() is formatted as "M/D/YYYY H:M:S AM/PM", this truncates it to only what is left of the first space.
    sDateBox.Value = Left(Now(), InStr(1, Now(), " ")) 'Now() is formatted as "M/D/YYYY H:M:S AM/PM", this truncates it to only what is left of the first space.
End Sub

'Show a warning when plywood is changed from HDO
Private Sub PlyNameBox_KeyPress(ByVal KeyAscii As MSForms.ReturnInteger)
    If KeyAscii = 27 Then ColumnCreator.Hide
End Sub
Private Sub PlyNameBox_KeyUp(ByVal KeyAscii As MSForms.ReturnInteger, ByVal Shift As Integer)
    If UCase(ColumnCreator.PlyNameBox.Value) <> "HDO" Then
        ColumnCreator.notHDOwarn.Visible = True
    Else
        ColumnCreator.notHDOwarn.Visible = False
    End If
End Sub
Private Sub WidthBox_KeyUp(ByVal KeyAscii As MSForms.ReturnInteger, ByVal Shift As Integer)
    'Update the plywood layout sketch
    Call UpdatePly.UpdatePly(0)
    
    'Check that x, y, z inputs are within the defined limits
    If CheckInputs(ConvertToNum(WidthBox.Value), ConvertToNum(LengthBox.Value), ConvertToNum(HeightBox.Value), ConvertToNum(QuantityBox.Value), 1) = 0 Then
        Call UpdatePly.DisableDrawingButtons
    ElseIf CheckInputs(ConvertToNum(WidthBox.Value), ConvertToNum(LengthBox.Value), ConvertToNum(HeightBox.Value), ConvertToNum(QuantityBox.Value), 1) = 1 Then
        Call UpdatePly.EnableDrawingButtons
    End If
    
    'If an error message is visible, disable the drawing button
    If ColumnCreator.txtPlyError.Visible = True Then
        Call UpdatePly.DisableDrawingButtons
    End If
    
    'Auto-generate sheet name
    Call AutoSheetName
End Sub
Private Sub LengthBox_KeyUp(ByVal KeyAscii As MSForms.ReturnInteger, ByVal Shift As Integer)
    'Update the plywood layout sketch
    Call UpdatePly.UpdatePly(0)

    'Check that x, y, z inputs are within the defined limits
    If CheckInputs(ConvertToNum(WidthBox.Value), ConvertToNum(LengthBox.Value), ConvertToNum(HeightBox.Value), ConvertToNum(QuantityBox.Value), 1) = 0 Then
        Call UpdatePly.DisableDrawingButtons
    ElseIf CheckInputs(ConvertToNum(WidthBox.Value), ConvertToNum(LengthBox.Value), ConvertToNum(HeightBox.Value), ConvertToNum(QuantityBox.Value), 1) = 1 Then
        Call UpdatePly.EnableDrawingButtons
    End If

    'If an error message is visible, disable the drawing button
    If ColumnCreator.txtPlyError.Visible = True Then
        Call UpdatePly.DisableDrawingButtons
    End If
    
    'Auto-generate sheet name
    Call AutoSheetName
End Sub
Private Sub HeightBox_KeyUp(ByVal KeyAscii As MSForms.ReturnInteger, ByVal Shift As Integer)
    'Update the plywood layout sketch
    Call UpdatePly.UpdatePly(0)
    Call UpdatePly.UpdatePly(3)
    
    'Check that x, y, z inputs are within the defined limits
    If CheckInputs(ConvertToNum(WidthBox.Value), ConvertToNum(LengthBox.Value), ConvertToNum(HeightBox.Value), ConvertToNum(QuantityBox.Value), 1) = 0 Then
        Call UpdatePly.DisableDrawingButtons
    ElseIf CheckInputs(ConvertToNum(WidthBox.Value), ConvertToNum(LengthBox.Value), ConvertToNum(HeightBox.Value), ConvertToNum(QuantityBox.Value), 1) = 1 Then
        Call UpdatePly.EnableDrawingButtons
    End If
    
    'If an error message is visible, disable the drawing button
    If ColumnCreator.txtPlyError.Visible = True Then
        Call UpdatePly.DisableDrawingButtons
    End If
End Sub
Private Sub QuantityBox_KeyUp(ByVal KeyAscii As MSForms.ReturnInteger, ByVal Shift As Integer)
    'Check that x, y, z inputs are within the defined limits
    If CheckInputs(ConvertToNum(WidthBox.Value), ConvertToNum(LengthBox.Value), ConvertToNum(HeightBox.Value), ConvertToNum(QuantityBox.Value), 1) = 0 Then
        Call UpdatePly.DisableDrawingButtons
    ElseIf CheckInputs(ConvertToNum(WidthBox.Value), ConvertToNum(LengthBox.Value), ConvertToNum(HeightBox.Value), ConvertToNum(QuantityBox.Value), 1) = 1 Then
        Call UpdatePly.EnableDrawingButtons
    End If

    'If an error message is visible, disable the drawing button
    If ColumnCreator.txtPlyError.Visible = True Then
        Call UpdatePly.DisableDrawingButtons
    End If
End Sub


Private Sub WidthBox_KeyPress(ByVal KeyAscii As MSForms.ReturnInteger)
    If KeyAscii = 27 Then ColumnCreator.Hide
    Call KeyInputRestrictorFtIn(KeyAscii, WidthBox.Value)
End Sub
Private Sub LengthBox_KeyPress(ByVal KeyAscii As MSForms.ReturnInteger)
    If KeyAscii = 27 Then ColumnCreator.Hide
    Call KeyInputRestrictorFtIn(KeyAscii, LengthBox.Value)
End Sub
Private Sub HeightBox_KeyPress(ByVal KeyAscii As MSForms.ReturnInteger)
    If KeyAscii = 27 Then ColumnCreator.Hide
    Call KeyInputRestrictorFtIn(KeyAscii, HeightBox.Value)
End Sub
Private Sub QuantityBox_KeyPress(ByVal KeyAscii As MSForms.ReturnInteger)
    If KeyAscii = 27 Then ColumnCreator.Hide
    Call KeyInputRestrictorNum(KeyAscii)
End Sub

Private Sub ClampSizeButton1_KeyPress(ByVal KeyAscii As MSForms.ReturnInteger)
    If KeyAscii = 27 Then ColumnCreator.Hide
End Sub
Private Sub ClampSizeButton2_KeyPress(ByVal KeyAscii As MSForms.ReturnInteger)
    If KeyAscii = 27 Then ColumnCreator.Hide
End Sub
Private Sub ClampSizeButton3_KeyPress(ByVal KeyAscii As MSForms.ReturnInteger)
    If KeyAscii = 27 Then ColumnCreator.Hide
End Sub
Private Sub ClampSizeButton4_KeyPress(ByVal KeyAscii As MSForms.ReturnInteger)
    If KeyAscii = 27 Then ColumnCreator.Hide
End Sub
Private Sub CommandButton1_KeyPress(ByVal KeyAscii As MSForms.ReturnInteger)
    If KeyAscii = 27 Then ColumnCreator.Hide
End Sub

Private Sub ProjectNameBox_KeyPress(ByVal KeyAscii As MSForms.ReturnInteger)
    If KeyAscii = 27 Then ColumnCreator.Hide
End Sub
Private Sub ProjectTitleBox_KeyPress(ByVal KeyAscii As MSForms.ReturnInteger)
    If KeyAscii = 27 Then ColumnCreator.Hide
End Sub
Private Sub ProjectAddressBox_KeyPress(ByVal KeyAscii As MSForms.ReturnInteger)
    If KeyAscii = 27 Then ColumnCreator.Hide
End Sub
Private Sub DateBox_KeyPress(ByVal KeyAscii As MSForms.ReturnInteger)
    If KeyAscii = 27 Then ColumnCreator.Hide
End Sub
Private Sub SheetIssuedForBox_KeyPress(ByVal KeyAscii As MSForms.ReturnInteger)
    If KeyAscii = 27 Then ColumnCreator.Hide
End Sub
Private Sub ScaleBox_KeyPress(ByVal KeyAscii As MSForms.ReturnInteger)
    If KeyAscii = 27 Then ColumnCreator.Hide
End Sub
Private Sub DrawnByBox_KeyPress(ByVal KeyAscii As MSForms.ReturnInteger)
    If KeyAscii = 27 Then ColumnCreator.Hide
End Sub
Private Sub JobNoBox_KeyPress(ByVal KeyAscii As MSForms.ReturnInteger)
    If KeyAscii = 27 Then ColumnCreator.Hide
End Sub
Private Sub SheetBox_KeyPress(ByVal KeyAscii As MSForms.ReturnInteger)
    If KeyAscii = 27 Then ColumnCreator.Hide
End Sub
Private Sub SuffixBox_KeyPress(ByVal KeyAscii As MSForms.ReturnInteger)
    If KeyAscii = 27 Then ColumnCreator.Hide
End Sub
Private Sub AreaBox_KeyPress(ByVal KeyAscii As MSForms.ReturnInteger)
    If KeyAscii = 27 Then ColumnCreator.Hide
End Sub
Private Sub SaveButton_KeyPress(ByVal KeyAscii As MSForms.ReturnInteger)
    If KeyAscii = 27 Then ColumnCreator.Hide
End Sub
Private Sub LoadButton_KeyPress(ByVal KeyAscii As MSForms.ReturnInteger)
    If KeyAscii = 27 Then ColumnCreator.Hide
End Sub

Private Sub ProjectNameBox_KeyUp(ByVal KeyCode As MSForms.ReturnInteger, ByVal Shift As Integer)
    If LCase(ProjectNameBox.Value) = "open" Then
        MultiPage1.Pages.Item("Page2").Visible = True
    End If
    If LCase(ProjectNameBox.Value) = "close" Then
        MultiPage1.Pages.Item("Page2").Visible = False
    End If
End Sub


'[-=-][-=-][-=-][-=-][-=-][-=-][-=-][-=-][-=-][-=-][-=-][-=-][-=-][-=-]
'                        Scissor clamp section
'[-=-][-=-][-=-][-=-][-=-][-=-][-=-][-=-][-=-][-=-][-=-][-=-][-=-][-=-]


Private Sub sWidthBox_KeyUp(ByVal KeyAscii As MSForms.ReturnInteger, ByVal Shift As Integer)
    'Update the plywood layout sketch
    Call sUpdatePly.sUpdatePly(0)

    'Check that x, y, z inputs are within the defined limits
    If CheckInputs(ConvertToNum(sWidthBox.Value), ConvertToNum(sLengthBox.Value), ConvertToNum(sHeightBox.Value), ConvertToNum(sQuantityBox.Value), 1) = 0 Then
        Call sUpdatePly.sDisableDrawingButtons
    ElseIf CheckInputs(ConvertToNum(sWidthBox.Value), ConvertToNum(sLengthBox.Value), ConvertToNum(sHeightBox.Value), ConvertToNum(sQuantityBox.Value), 1) = 1 Then
        Call sUpdatePly.sEnableDrawingButtons
    End If
    
    'Update max allowable height
    Call sUpdatePly.sCheckHeight(ConvertToNum(sWidthBox.Value), ConvertToNum(sLengthBox.Value), ConvertToNum(sHeightBox.Value))
    
    'If an error message is visible, disable the drawing button
    If ColumnCreator.stxtPlyError.Visible = True Then
        Call sUpdatePly.sDisableDrawingButtons
    End If
    
    'Auto-generate sheet name
    Call AutoSheetName
    
End Sub
Private Sub sLengthBox_KeyUp(ByVal KeyAscii As MSForms.ReturnInteger, ByVal Shift As Integer)
    'Update the plywood layout sketch
    Call sUpdatePly.sUpdatePly(0)

    'Check that x, y, z inputs are within the defined limits
    If CheckInputs(ConvertToNum(sWidthBox.Value), ConvertToNum(sLengthBox.Value), ConvertToNum(sHeightBox.Value), ConvertToNum(sQuantityBox.Value), 1) = 0 Then
        Call sUpdatePly.sDisableDrawingButtons
    ElseIf CheckInputs(ConvertToNum(sWidthBox.Value), ConvertToNum(sLengthBox.Value), ConvertToNum(sHeightBox.Value), ConvertToNum(sQuantityBox.Value), 1) = 1 Then
        Call sUpdatePly.sEnableDrawingButtons
    End If
    
    'Update max allowable height
    Call sUpdatePly.sCheckHeight(ConvertToNum(sWidthBox.Value), ConvertToNum(sLengthBox.Value), ConvertToNum(sHeightBox.Value))

    'If an error message is visible, disable the drawing button
    If ColumnCreator.stxtPlyError.Visible = True Then
        Call sUpdatePly.sDisableDrawingButtons
    End If
    
    'Auto-generate sheet name
    Call AutoSheetName
    
End Sub
Private Sub sHeightBox_KeyUp(ByVal KeyAscii As MSForms.ReturnInteger, ByVal Shift As Integer)
    'Update the plywood layout sketch
    Call sUpdatePly.sUpdatePly(0)
    Call sUpdatePly.sUpdatePly(3)

    'Check that x, y, z inputs are within the defined limits
    If CheckInputs(ConvertToNum(sWidthBox.Value), ConvertToNum(sLengthBox.Value), ConvertToNum(sHeightBox.Value), ConvertToNum(sQuantityBox.Value), 1) = 0 Then
        Call sUpdatePly.sDisableDrawingButtons
    ElseIf CheckInputs(ConvertToNum(sWidthBox.Value), ConvertToNum(sLengthBox.Value), ConvertToNum(sHeightBox.Value), ConvertToNum(sQuantityBox.Value), 1) = 1 Then
        Call sUpdatePly.sEnableDrawingButtons
    End If
    
    'If an error message is visible, disable the drawing button
    If ColumnCreator.stxtPlyError.Visible = True Then
        Call sUpdatePly.sDisableDrawingButtons
    End If
    
    'Update max allowable height
    Call sUpdatePly.sCheckHeight(ConvertToNum(sWidthBox.Value), ConvertToNum(sLengthBox.Value), ConvertToNum(sHeightBox.Value))
    
End Sub
Private Sub sQuantityBox_KeyUp(ByVal KeyAscii As MSForms.ReturnInteger, ByVal Shift As Integer)
    'Check that x, y, z inputs are within the defined limits
    If CheckInputs(ConvertToNum(sWidthBox.Value), ConvertToNum(sLengthBox.Value), ConvertToNum(sHeightBox.Value), ConvertToNum(sQuantityBox.Value), 1) = 0 Then
        Call sUpdatePly.sDisableDrawingButtons
    ElseIf CheckInputs(ConvertToNum(sWidthBox.Value), ConvertToNum(sLengthBox.Value), ConvertToNum(sHeightBox.Value), ConvertToNum(sQuantityBox.Value), 1) = 1 Then
        Call sUpdatePly.sEnableDrawingButtons
    End If
    
    'If an error message is visible, disable the drawing button
    If ColumnCreator.stxtPlyError.Visible = True Then
        Call sUpdatePly.sDisableDrawingButtons
    End If
    
    'Update max allowable height. Calling this function here to prevent changes the quantity from erasing data shown previously.
    Call sUpdatePly.sCheckHeight(ConvertToNum(sWidthBox.Value), ConvertToNum(sLengthBox.Value), ConvertToNum(sHeightBox.Value))
    
End Sub

Private Sub slblAxis_Click()
    If ColumnCreator.slblAxis.Caption = "X" Then
        ColumnCreator.slblAxis.Caption = "Y"
    ElseIf ColumnCreator.slblAxis.Caption = "Y" Then
        ColumnCreator.slblAxis.Caption = "X"
    End If
    Call sUpdatePly.sUpdatePly(0) 'Update the plywood layout sketch
End Sub

Private Sub sWidthBox_KeyPress(ByVal KeyAscii As MSForms.ReturnInteger)
    If KeyAscii = 27 Then ColumnCreator.Hide
    Call KeyInputRestrictorFtIn(KeyAscii, sWidthBox.Value)
End Sub
Private Sub sLengthBox_KeyPress(ByVal KeyAscii As MSForms.ReturnInteger)
    If KeyAscii = 27 Then ColumnCreator.Hide
    Call KeyInputRestrictorFtIn(KeyAscii, sLengthBox.Value)
End Sub
Private Sub sHeightBox_KeyPress(ByVal KeyAscii As MSForms.ReturnInteger)
    If KeyAscii = 27 Then ColumnCreator.Hide
    Call KeyInputRestrictorFtIn(KeyAscii, sHeightBox.Value)
End Sub
Private Sub sQuantityBox_KeyPress(ByVal KeyAscii As MSForms.ReturnInteger)
    If KeyAscii = 27 Then ColumnCreator.Hide
    Call KeyInputRestrictorNum(KeyAscii)
End Sub

'Show a warning when plywood is changed from HDO
Private Sub sPlyNameBox_KeyPress(ByVal KeyAscii As MSForms.ReturnInteger)
    If KeyAscii = 27 Then ColumnCreator.Hide
End Sub
Private Sub sPlyNameBox_KeyUp(ByVal KeyAscii As MSForms.ReturnInteger, ByVal Shift As Integer)
    If UCase(ColumnCreator.sPlyNameBox.Value) <> "HDO" Then
        ColumnCreator.snotHDOwarn.Visible = True
    Else
        ColumnCreator.snotHDOwarn.Visible = False
    End If
End Sub

Private Sub sClampSizeButton1_KeyPress(ByVal KeyAscii As MSForms.ReturnInteger)
    If KeyAscii = 27 Then ColumnCreator.Hide
End Sub
Private Sub sClampSizeButton2_KeyPress(ByVal KeyAscii As MSForms.ReturnInteger)
    If KeyAscii = 27 Then ColumnCreator.Hide
End Sub
Private Sub sClampSizeButton3_KeyPress(ByVal KeyAscii As MSForms.ReturnInteger)
    If KeyAscii = 27 Then ColumnCreator.Hide
End Sub
Private Sub sClampSizeButton4_KeyPress(ByVal KeyAscii As MSForms.ReturnInteger)
    If KeyAscii = 27 Then ColumnCreator.Hide
End Sub
Private Sub sboxPlySeams_KeyPress(ByVal KeyAscii As MSForms.ReturnInteger)
    If KeyAscii = 27 Then ColumnCreator.Hide
End Sub
Private Sub sboxPlySeams_KeyUp(ByVal KeyAscii As MSForms.ReturnInteger, ByVal Shift As Integer)
    Call sUpdatePly.sUpdatePly(1)
End Sub
Private Sub sProjectNameBox_KeyPress(ByVal KeyAscii As MSForms.ReturnInteger)
    If KeyAscii = 27 Then ColumnCreator.Hide
End Sub
Private Sub sProjectTitleBox_KeyPress(ByVal KeyAscii As MSForms.ReturnInteger)
    If KeyAscii = 27 Then ColumnCreator.Hide
End Sub
Private Sub sProjectAddressBox_KeyPress(ByVal KeyAscii As MSForms.ReturnInteger)
    If KeyAscii = 27 Then ColumnCreator.Hide
End Sub
Private Sub sDateBox_KeyPress(ByVal KeyAscii As MSForms.ReturnInteger)
    If KeyAscii = 27 Then ColumnCreator.Hide
End Sub
Private Sub sSheetIssuedForBox_KeyPress(ByVal KeyAscii As MSForms.ReturnInteger)
    If KeyAscii = 27 Then ColumnCreator.Hide
End Sub
Private Sub sScaleBox_KeyPress(ByVal KeyAscii As MSForms.ReturnInteger)
    If KeyAscii = 27 Then ColumnCreator.Hide
End Sub
Private Sub sDrawnByBox_KeyPress(ByVal KeyAscii As MSForms.ReturnInteger)
    If KeyAscii = 27 Then ColumnCreator.Hide
End Sub
Private Sub sJobNoBox_KeyPress(ByVal KeyAscii As MSForms.ReturnInteger)
    If KeyAscii = 27 Then ColumnCreator.Hide
End Sub
Private Sub sSheetBox_KeyPress(ByVal KeyAscii As MSForms.ReturnInteger)
    If KeyAscii = 27 Then ColumnCreator.Hide
End Sub
Private Sub sSuffixBox_KeyPress(ByVal KeyAscii As MSForms.ReturnInteger)
    If KeyAscii = 27 Then ColumnCreator.Hide
End Sub
Private Sub sAreaBox_KeyPress(ByVal KeyAscii As MSForms.ReturnInteger)
    If KeyAscii = 27 Then ColumnCreator.Hide
End Sub
Private Sub sSaveButton_KeyPress(ByVal KeyAscii As MSForms.ReturnInteger)
    If KeyAscii = 27 Then ColumnCreator.Hide
End Sub
Private Sub sLoadButton_KeyPress(ByVal KeyAscii As MSForms.ReturnInteger)
    If KeyAscii = 27 Then ColumnCreator.Hide
End Sub

Private Sub sSaveButton_Click()
    Dim SheetDataFilePath As String
    Dim SheetDataFileName As String
    Dim SheetDataFilePathAndName As String
    Dim sHostName As String
    Dim fso As New FileSystemObject
    Dim oFile As Object
    
    'Set file name and path
    SheetDataFilePath = "C:\ProgramData\Autodesk\VBA Saved Files"
    SheetDataFileName = "Scissor Clamp Column Sheet Data.txt"
    SheetDataPathAndName = SheetDataFilePath & "\" & SheetDataFileName
    
    'Create folder path
    If Not FolderExists("C:\ProgramData") Then
        FolderCreate ("C:\ProgramData")
    End If
    If Not FolderExists("C:\ProgramData\Autodesk") Then
        FolderCreate ("C:\ProgramData\Autodesk")
    End If
    If Not FolderExists(SheetDataFilePath) Then
        FolderCreate (SheetDataFilePath)
    End If

    'Create a text file and write the following lines
    Set oFile = fso.CreateTextFile(SheetDataPathAndName, True) 'True allows overwriting
    
    oFile.WriteLine sProjectNameBox.Value
    oFile.WriteLine sProjectTitleBox.Value
    oFile.WriteLine sProjectAddressBox.Value
    oFile.WriteLine sDateBox.Value
    oFile.WriteLine sSheetIssuedForBox.Value
    oFile.WriteLine sScaleBox.Value
    oFile.WriteLine sDrawnByBox.Value
    oFile.WriteLine sJobNoBox.Value
    oFile.WriteLine sSheetBox.Value
    oFile.WriteLine sSuffixBox.Value
    oFile.WriteLine sAreaBox.Value
    
    oFile.Close
    Set fso = Nothing
    Set oFile = Nothing
End Sub
Public Sub sLoadButton_Click()
    Dim SheetDataFilePath As String
    Dim SheetDataFileName As String
    Dim SheetDataFilePathAndName As String
    Dim mystring As String
    Dim temp_lines(1 To 11) As String
    
    SheetDataFilePath = "C:\ProgramData\Autodesk\VBA Saved Files"
    SheetDataFileName = "Scissor Clamp Column Sheet Data.txt"
    SheetDataPathAndName = SheetDataFilePath & "\" & SheetDataFileName
    
    If Dir(SheetDataPathAndName) = "" Then
        MsgBox ("Error: You can't load a file you haven't saved")
        Exit Sub
    End If
    
    Open SheetDataPathAndName For Input As #1
    i = 1
    
    Do While Not EOF(1)
        Line Input #1, mystring
        temp_lines(i) = mystring
        i = i + 1
    Loop
    Close #1
    
    'Load the following lines to the corresponding variables
    sProjectNameBox.Value = temp_lines(1)
    sProjectTitleBox.Value = temp_lines(2)
    sProjectAddressBox.Value = temp_lines(3)
    sDateBox.Value = temp_lines(4)
    sSheetIssuedForBox.Value = temp_lines(5)
    sScaleBox.Value = temp_lines(6)
    sDrawnByBox.Value = temp_lines(7)
    sJobNoBox.Value = temp_lines(8)
    sSheetBox.Value = temp_lines(9)
    sSuffixBox.Value = temp_lines(10)
    sAreaBox.Value = temp_lines(11)
End Sub

Attribute VB_Name = "ColumnCreatorRun"
Sub CallUserForm()
    ColumnCreator.show
End Sub

Attribute VB_Name = "ConvertFeetInchesToNumber"

Function ConvertToNum(StringInput) As Double

    '####################################################################################################################################################################################
    'This function has the added ability to consider fractions e.g. 10'-5 1/2"
    'str_temp1 = 10
    'str_temp2 = 5
    'str_temp3 = 1
    'str_temp4 = 2
    '####################################################################################################################################################################################
    
    'On Error GoTo ConvertToNumErrorHandler
    
    Dim neg_tog As Integer
    Dim found_num As Integer
    Dim str_temp1 As String
    Dim str_temp2 As String
    Dim str_temp3 As String
    Dim str_temp4 As String

    neg_tog = 1
    
    'Convert empty values or just a . to 0
    If StringInput = "" Or StringInput = " " Or StringInput = "." Then
        ConvertToNum = 0
        Exit Function
    End If
    
    var_in = StringInput 'Input value. This function can handle the following formats:
        '125                125
        '125.5              125.5
        '125.5"             125.5
        '10'                120
        '10'-5.5"           125.5
        '10'5.5             125.5
        '10'5.5"            125.5
        '10'-5.5            125.5
        '10 5.5             125.5
        '10'.5              120.5
        '10'-5 1/2"         125.5
        '10'5 1/2"          125.5
        '10'5-1/2"          125.5
        '10' 1/2"           120.5
        '10' 5.5/2"         122.75
        '10' 5.5 5/2"       128
        '10' 5.5 5.5/2"     128.25
        
    str_temp1 = "" 'Reset to blank strings
    str_temp2 = ""
    str_temp3 = ""
    str_temp4 = ""
    
    'Check if string contains no numeric characters, then the output is 0
    For iCnt0 = 1 To Len(var_in)
        If IsNumeric(Mid(var_in, iCnt0, 1)) Then
            GoTo TheresANumberInThere
        ElseIf iCnt0 = Len(var_in) Then
            out_num = 0
            GoTo SkipConvertToNumErrorHandler
        End If
    Next iCnt0
TheresANumberInThere:

    'Check if number is negative, if it is, remove the negative sign and process the positive number, then make it negative again later
    If Mid(var_in, 1, 1) = "-" Then
        neg_tog = -1
        var_in = Right(var_in, Len(var_in) - 1)
    End If

    'Read the input box 1 character at a time left to right. If the char is numeric or a ".", add it to str_temp1. If not, stop reading
    found_num = 0
    For iCnt1 = 1 To Len(var_in)
        If IsNumeric(Mid(var_in, iCnt1, 1)) Or Mid(var_in, iCnt1, 1) = "." Then 'Record numbers and periods
            str_temp1 = str_temp1 & Mid(var_in, iCnt1, 1)
            found_num = 1
        ElseIf found_num = 0 Then 'If no number has been found yet, do nothing, regardless of character
        ElseIf found_num = 1 Then 'If numbers have been found, and the character isn't a number of period, exit the loop
            Exit For
        End If
    Next iCnt1
    
    'Start again 1 char after where the last loop left off and store numeric characters until a non-numeric, non-period character is encountered
    found_num = 0
    For iCnt2 = iCnt1 + 1 To Len(var_in)
        If IsNumeric(Mid(var_in, iCnt2, 1)) Or Mid(var_in, iCnt2, 1) = "." Then 'Record numbers and periods
            str_temp2 = str_temp2 & Mid(var_in, iCnt2, 1)
            found_num = 1
        ElseIf found_num = 0 Then 'If no number has been found yet, do nothing, regardless of character
        ElseIf found_num = 1 Then 'If numbers have been found, and the character isn't a number of period, exit the loop
            Exit For
        End If
    Next iCnt2
    
    'str_temp3 and str_temp4 are for fractions and may not be used
    'Start again 1 char after where the last loop left off
    found_num = 0
    For iCnt3 = iCnt2 + 1 To Len(var_in)
        If IsNumeric(Mid(var_in, iCnt3, 1)) Or Mid(var_in, iCnt3, 1) = "." Then 'Record numbers and periods
            str_temp3 = str_temp3 & Mid(var_in, iCnt3, 1)
            found_num = 1
        ElseIf found_num = 0 Then 'If no number has been found yet, do nothing, regardless of character
        ElseIf found_num = 1 Then 'If numbers have been found, and the character isn't a number of period, exit the loop
            Exit For
        End If
    Next iCnt3
    
    found_num = 0
    For iCnt4 = iCnt3 + 1 To Len(var_in)
        If IsNumeric(Mid(var_in, iCnt4, 1)) Or Mid(var_in, iCnt4, 1) = "." Then 'Record numbers and periods
            str_temp4 = str_temp4 & Mid(var_in, iCnt4, 1)
            found_num = 1
        ElseIf found_num = 0 Then 'If no number has been found yet, do nothing, regardless of character
        ElseIf found_num = 1 Then 'If numbers have been found, and the character isn't a number of period, exit the loop
            Exit For
        End If
    Next iCnt4
    
    'MsgBox "str_temp3: " & str_temp3 & vbNewLine & "str_temp4: " & str_temp4
    
    If str_temp1 <> "" And str_temp1 <> "." And _
       str_temp2 <> "" And str_temp2 <> "." And _
       str_temp3 <> "" And str_temp3 <> "." And _
       str_temp4 <> "" And str_temp4 <> "." Then
            If CDbl(str_temp4) = 0 Then
                out_num = 0
            Else
                out_num = 12 * CDbl(str_temp1) + CDbl(str_temp2) + CDbl(str_temp3) / CDbl(str_temp4)
            End If
            
    ElseIf str_temp1 <> "" And str_temp1 <> "." And _
           str_temp2 <> "" And str_temp2 <> "." And _
           str_temp3 <> "" And str_temp3 <> "." Then
            If CDbl(str_temp3) = 0 Then
                out_num = 0
            Else
                out_num = 12 * CDbl(str_temp1) + CDbl(str_temp2) / CDbl(str_temp3)
            End If

    ElseIf str_temp1 <> "" And str_temp1 <> "." And _
           str_temp2 <> "" And str_temp2 <> "." Then
            out_num = 12 * CDbl(str_temp1) + CDbl(str_temp2)
            
    ElseIf str_temp1 <> "" And str_temp1 <> "." Then
        If Mid(var_in, iCnt1, 1) = "'" Then
            out_num = CDbl(str_temp1) * 12
        Else
            out_num = CDbl(str_temp1)
        End If
    Else
        out_num = 0
    End If
  
    'Apply the negative value and set the function output
    ConvertToNum = neg_tog * out_num
    
    GoTo SkipConvertToNumErrorHandler
ConvertToNumErrorHandler:
        Exit Function
    On Error GoTo 0
SkipConvertToNumErrorHandler:
End Function

Attribute VB_Name = "ConvertNumberToFeetInches"

Function ConvertFtIn(ByVal num) As String

    '================================================
    'This version properly converts negative numbers
    '================================================
    
    Dim xFt As String
    Dim xIn As String
    Dim xFra As String
    Dim strNeg As String
    
    If num = "" Or num = " " Then
        ConvertFtIn = 0
        Exit Function
    End If
    
    'If the number is negative, make it positive, then multiply add a "-" character at the very end
    If num < 0 Then
        strNeg = "-"
        num = num * -1
    Else
        strNeg = ""
    End If
    
    'Add a hair then round DOWN to nearest 1/8th inch
    'num = (Round((num + 0.01) * 8 + 0.5, 0) - 1) / 8
    
    'Round to the nearest 1/8th inch
    num = (Round((num * 8) - 0.000000001, 0)) / 8
    
    xFt = CStr(Int(Round(num / 12, 3)))
    xIn = CStr(num - 12 * Int(Round(num / 12, 3)))
    
    'If inches are not an integer convert decimal to fraction
    If Round(num - Int(Round(num, 3)), 3) <> 0 Then
        xFra = Dec2Frac(12 * ((num / 12) - Int(num / 12)) - Int(num - 12 * Int(num / 12))) 'Inches minus integer inches
        xIn = Int(num - 12 * Int(num / 12)) 'Redefine inches without the fraction
    End If
    
    'If ft = 0 as a string don't print ft
    If xFt = "0" Then
        If Round(num - Int(Round(num, 3)), 3) <> 0 Then
            ConvertFtIn = strNeg & xIn & Space(1) & xFra & """"  'Ft = 0 and inches are fractional
        Else
            ConvertFtIn = strNeg & xIn & """"    'Ft = 0 and inches are whole integers
        End If
    Else
        If Round(num - Int(Round(num, 3)), 3) <> 0 Then
            ConvertFtIn = strNeg & xFt & "'-" & xIn & Space(1) & xFra & """" 'Ft <> 0 and inches are fractional
        Else
            ConvertFtIn = strNeg & xFt & "'-" & xIn & """"   'Ft <> 0 and inches are whole integers
        End If
    End If
    
End Function

Public Function Dec2Frac(ByVal dFraction As Double) As String
    
    'Type: Public Function
    'Name: Decimal to Fraction Converter
    'Purpose: Converts a passed decimal to a fraction
    'Limitations: Will not convert to mixed fractions
    'Author: Unknown
    'Arguments: dFraction is the decimal to convert
    'Return Value: String representingthe fraction
    'Useage: Dec2Frac(.125)
    'Notes:
    
    Dim df As Double
    Dim lUpperPart As Long
    Dim lLowerPart As Long
    
    lUpperPart = 1
    lLowerPart = 1
    
    dFraction = Round(dFraction, 3) 'Cleans up messy double values
    df = lUpperPart / lLowerPart
    
    While (df <> dFraction)
        If (df < dFraction) Then
            lUpperPart = lUpperPart + 1
        Else
            lLowerPart = lLowerPart + 1
            lUpperPart = dFraction * lLowerPart
        End If
        df = lUpperPart / lLowerPart
    Wend
    
    Dec2Frac = CStr(lUpperPart) & "/" & CStr(lLowerPart)

End Function

Attribute VB_Name = "GetPlySeams_Function"
Public Function GetPlySeams(ByVal x, ByVal y, ByVal z) As Double()
    Dim ply_width_x As Double
    Dim ply_width_y As Double
    Dim ply_top_ht As Double
    Dim ply_bot_n As Integer 'Number of 8'-0" by x'-x" sheets on the bottom of the column
    Dim ply_top_ht_min As Double: ply_top_ht_min = 6 'Smallest allowable strip of plywood at top of column
    Dim ply_seams_fun() As Double '1 dimensional matrix that stores vertical length of each ply piece
    Dim max_ply_ht As Double
    
    If ColumnCreator.MultiPage1.Value = 0 Then 'GATES COLUMNS

        'Add 1.5 inches to nominal width for ply sheet width
        ply_width_x = x + 1.5
        ply_width_y = y + 1.5
        
    ElseIf ColumnCreator.MultiPage1.Value = 1 Then 'SCISSOR CLAMP COLUMNS
        'x: Add 0 inches to nominal width for ply sheet width on the short side
        'y: Add 4.5 inches to nominal width for ply sheet width on the long side
        ply_width_x = x
        ply_width_y = y + 4.5
    End If
    
    'If column is very wide, use rotated sheets and thus 48" max height
    If Round(ply_width_x, 3) > 48 Or Round(ply_width_y, 3) > 48 Then
        max_ply_ht = 48
    Else
        max_ply_ht = 96
    End If
    
    'Assume sheets aligned vertically. How many of those fit on the bottom and what is the remainder in inches on top?
    ply_top_ht = z - max_ply_ht * Int(Round(z / max_ply_ht, 3)) 'Int will floor to the nearest integer
    ply_bot_n = Int(Round(z / max_ply_ht, 3))

    'Add the typical sheets plus 1 if a smaller top ply is used
    ReDim ply_seams_fun(1 To ply_bot_n + Abs(Round(ply_top_ht, 3) <> 0))

    'If only a single sheet is required, use that and jump to the end
    If Round(z, 3) <= max_ply_ht Then
        ply_seams_fun(1) = z
        GoTo PlySeamsObtained
    End If
    
    'Start filling ply_seams_fun array with typical 8'-0" or 4'-0" sheets and fill the last value with the height of the top sheet, if any
    For i = 1 To ply_bot_n
        ply_seams_fun(i) = max_ply_ht
    Next i
    If Round(ply_top_ht, 3) <> 0 Then
        ply_seams_fun(UBound(ply_seams_fun)) = ply_top_ht
    End If
    
    'If top piece is too small and nonzero add 48" to it and use a 48" piece below it.
    If Round(ply_top_ht, 3) < Round(ply_top_ht_min, 3) And Round(ply_top_ht, 3) > 0 Then
        ply_top_ht = ply_top_ht + 48 * max_ply_ht / 96 '1/2 of max ply ht (24" or 48")
        ply_bot_n = Int(Round((z - 48 * max_ply_ht / 96 - ply_top_ht) / max_ply_ht, 3)) 'Recompute number of 8' or 4' ply pieces on the bottom, less the new top pieces
        ReDim ply_seams_fun(1 To ply_bot_n + 2) 'Delete old data in this array, resize it for the new ply arrangement
        
        For i = 1 To ply_bot_n
            ply_seams_fun(i) = max_ply_ht
        Next i
        ply_seams_fun(UBound(ply_seams_fun) - 1) = 48 * max_ply_ht / 96
        ply_seams_fun(UBound(ply_seams_fun)) = ply_top_ht
    End If
PlySeamsObtained:

    GetPlySeams = ply_seams_fun

End Function

Attribute VB_Name = "ImportMatrix_Function"

Public Function ImportMatrix(filepath) 'filepath string is specified in the main routine
    'Import a .csv file
    'Ignore first column and first row
    'All rows and columns must have the same number of entries
    'All values must be numeric
    
    Dim i As Integer: i = 0 'number of rows start at minimum)
    Dim j As Integer        'number of columns (start at minimum)
    Dim n_rows_tot As Integer: n_rows_tot = 0
    Dim a As Integer
    Dim b As Integer
    
    Dim mystring As String
    Dim temp_row() As String
    Dim return_matrix() As Integer

    'Find the total number of rows and columns to redim the array to the proper size
    Open filepath For Input As #1
    Do While Not EOF(1)
        Line Input #1, mystring
        n_rows_tot = n_rows_tot + 1
    Loop
    Close #1
    temp_row = Split(mystring, ",") 'Load 1 row to read its length
    
    ReDim return_matrix(n_rows_tot - 1, UBound(temp_row)) 'Redim array to maximum file rows and columns (n_rows_tot and UBound(temp_row) respectively)
                                                          'Can only modify LAST dimension using redim with preserve.
                                                          'This avoids constantly redimming the array with preserve and worrying about which dimension is being changed.
    
    Open filepath For Input As #1           'Reopens the file to start a new loop.
    Do While Not EOF(1)                     'Do while the end of file hasn't been reached
        Line Input #1, mystring             'Reads file one full row at a time as a string
        temp_row = Split(mystring, ",")     'Deliminates the row by "," and stores each value into the temp_row array as a string.

        For j = 0 To UBound(temp_row)                               'Cycle through each entry in a single row
            return_matrix(i, j) = CInt(temp_row(j))                 'Place each entry of temp_row into the output matrix and convert it from string to integer
        Next j

        i = i + 1 'Count ticks up for the next matrix row
    Loop
    
    ImportMatrix = return_matrix 'Reassigns matrix to function name for output
    
    Close #1 'Close the file
    
End Function

Attribute VB_Name = "KeyPressModuleNum"
Public Function KeyInputRestrictorNum(ByVal KeyAscii As MSForms.ReturnInteger)
    If KeyAscii < 48 Or KeyAscii > 57 Then                                                              'If the key is a number it is allowed. If the key is not a number then...
        KeyAscii = 0                                                                                        'BLOCK the keypress
    End If
End Function

Attribute VB_Name = "KeypressModuleFtIn"
Public Function KeyInputRestrictorFtIn(ByVal KeyAscii As MSForms.ReturnInteger, BoxValue)
    If KeyAscii < 48 Or KeyAscii > 57 Then                                                              'If the key is a number it is allowed. If the key is not a number then...
        If BoxValue = "" And (KeyAscii = 34 Or KeyAscii = 39 Or KeyAscii = 45 Or KeyAscii = 46) Then        'If this keypress is the first character and it's a ' " - or . then...
            KeyAscii = 0                                                                                        'BLOCK the keypress
        End If
        If KeyAscii = 34 Or KeyAscii = 39 Or KeyAscii = 45 Or KeyAscii = 46 Then                            'If key is " ' - or . then ALLOW the keypress
        Else                                                                                                'If key is not number and not " ' - or . then...
            KeyAscii = 0                                                                                        'BLOCK the keypress
        End If
    End If
End Function

Attribute VB_Name = "ReadSizes_Function"

Public Function ReadSizes(CSV_Ply) As Double() 'Initialize output array (Each line is 1 plywood size.
    Dim TempStr1 As String
    Dim TempStr2() As String
    Dim TempNum1() As Double
    Dim TempOutput() As Double

    On Error GoTo AbortReading
    
    'Abort if string is empty
    If CSV_Ply = "" Then
AbortReading:
        ReDim ReadSizes(1 To 1)
        ReDim TempOutput(1 To 1)
        TempOutput(1) = 0
        ReadSizes = TempOutput
        Exit Function
    End If
    
    'Read the given ply spacing and insert it into the ply_spacing array
    j = 1
    For i = 1 To Len(CSV_Ply)
        'Mid reads a specified number of characters from a string given a starting point.
        'In this case, mid starts reading at i and only reads 1 character at a time.
        'On commas or the last character, commit everything read up to that point
        If Mid(CSV_Ply, i, 1) = "," Or i = Len(CSV_Ply) Then
            If i = Len(CSV_Ply) Then
                TempStr1 = TempStr1 & Mid(CSV_Ply, i, 1)
            End If
            ReDim Preserve TempStr2(1 To j)
            TempStr2(j) = TempStr1
            j = j + 1
            TempStr1 = ""
        Else
            TempStr1 = TempStr1 & Mid(CSV_Ply, i, 1)
        End If
    Next i
    
    'Check if too many plywood dims are used
    If UBound(TempStr2) > 11 Then
        MsgBox ("Error: Too many ply sheets defined (max: 11).")
        GoTo AbortReading
    End If
    
    'Fill output array
    ReDim TempOutput(1 To UBound(TempStr2))
    ReDim ReadSizes(1 To UBound(TempStr2))
    For i = 1 To UBound(TempStr2)
        TempOutput(i) = ConvertToNum(TempStr2(i))
    Next i
    
    'Assign output variable
    ReadSizes = TempOutput
        
    On Error GoTo 0
End Function

Attribute VB_Name = "SetNewColumnStyles_Function"
Public Function BuildColumnStyles()
    'Create new dimension style and switch to it
    Dim NewDimStyle As AcadDimStyle
    Dim NewTextStyle As AcadTextStyle
    Dim iAltUnits As Integer
    Dim dDimScale As Double
    
    'Create new dim Style
    Set NewDimStyle = ThisDrawing.DimStyles.Add("VBA_Dimstyle")
    
    'Create text styles
    Set NewTextStyle = ThisDrawing.TextStyles.Add("VBA_txt_narrow")
    NewTextStyle.SetFont "Arial Narrow", False, False, 0, 0
    NewTextStyle.Height = 2
    
    Set NewTextStyle = ThisDrawing.TextStyles.Add("VBA_txt")
    NewTextStyle.SetFont "Arial", False, False, 0, 0
    NewTextStyle.Height = 2
    
    'Set newly created dim and text styles current
    ThisDrawing.ActiveDimStyle = NewDimStyle
    ThisDrawing.ActiveTextStyle = NewTextStyle
    
    'Alter the target "dimvar" values (these can be found in the dimstyle properties)
        'Lines Tab
        ThisDrawing.SetVariable "DIMCLRD", 151 'sets color for dimension lines
        ThisDrawing.SetVariable "DIMLTYPE", "ByBlock" 'sets dimension linetype
        ThisDrawing.SetVariable "DIMLWD", -2 'sets dimension lineweight, -2 is ByBlock
        ThisDrawing.SetVariable "DIMDLE", 1 'dim line extension past tick
        ThisDrawing.SetVariable "DIMDLI", 6 'default spacing between dimensions when using the DIMBASELINE command
        ThisDrawing.SetVariable "DIMCLRE", 150 'sets color for extension lines
        ThisDrawing.SetVariable "DIMLTEX1", "ByBlock" 'sets extension line 1 linetype
        ThisDrawing.SetVariable "DIMLTEX2", "ByBlock" 'sets extension line 2 linetype
        ThisDrawing.SetVariable "DIMLWE", -2 'sets extension line lineweight, -2 is by block
        ThisDrawing.SetVariable "DIMEXE", 1 'extension line extension beyond dim line
        ThisDrawing.SetVariable "DIMEXO", 1 'dim offset from origin
        
        'Symbols and Arrows Tab
        ThisDrawing.SetVariable "DIMSAH", 0 'use arrowhead blocks set by DIMBLK rather than DIMBLK1 and DIMBLK2
        ThisDrawing.SetVariable "DIMBLK", "_ARCHTICK" 'sets arrowhead block at dim lines
        ThisDrawing.SetVariable "DIMLDRBLK", "" 'sets arrowhead for leader line
        ThisDrawing.SetVariable "DIMASZ", 1.5 'arrowhead size
        
        'Text Tab
        ThisDrawing.SetVariable "DIMTXSTY", "VBA_txt" 'text style to use for this dimension style
        ThisDrawing.SetVariable "DIMCLRT", 150 'sets color for text
        ThisDrawing.SetVariable "DIMTXT", 2 'text height
        ThisDrawing.SetVariable "DIMTAD", 0 'horizontal text alignment, 0 is centered
        ThisDrawing.SetVariable "DIMJUST", 0 'vertical text alignment, 0 is centered
        ThisDrawing.SetVariable "DIMGAP", 1 'gap between text and dim lines
        ThisDrawing.SetVariable "DIMTIH", 0 'aligned with dimension line in conjunction with DIMTOH 'I think one is for dims inside the line and the other is for dims outside the line
        ThisDrawing.SetVariable "DIMTOH", 0 'aligned with dimension line in conjunctionw ith DIMTIH
        
        'Fit Tab
        ThisDrawing.SetVariable "DIMATFIT", 3 'for tight dimensions, moves text or arrows or both outside the extension lines
        ThisDrawing.SetVariable "DIMTMOVE", 0 '= 0, when you move text the dimension moves with it
        ThisDrawing.SetVariable "DIMSCALE", 1 'Controls dim size, recommendation: do not change!
        
        'Primary Units Tab
        ThisDrawing.SetVariable "DIMUNIT", 4 'Unit format, 1: scientific, 2: decimal, 3: engineering, 4: architectural, 5: fractional
        ThisDrawing.SetVariable "DIMTFAC", 1 'scales size of fractions
        ThisDrawing.SetVariable "DIMFRAC", 1 'fraction stacking format, 0: horizontal, 1: diagonal, 2: not stacked (1/2)
        ThisDrawing.SetVariable "DIMRND", 0.125 'Rounds dimension to this nearest value
        ThisDrawing.SetVariable "DIMZIN", 3 'Includes zero inches and suppresses zero feet

    'Copy new document dimvar settings into new dimstyle
    NewDimStyle.CopyFrom ThisDrawing
End Function

Attribute VB_Name = "UpdatePly"
Public Function UpdatePly(InputSource As Integer)

' # # # # # # # # # # # # # # # # # # # # # # # # # # # #
'                  FOR GATES COLUMNS
' # # # # # # # # # # # # # # # # # # # # # # # # # # # #

    'Input source of 0 is for changes from the x, y, and z boxes or from changing the axis
    'Input source of 1 is for changes from boxPlySeams
    'Input source of 2 is for changes from the window checkboxes or the window position dimensions
    'Input source of 3 is for changes from the z box only

    Dim x As Double
    Dim y As Double
    Dim z As Double

    x = ConvertToNum(ColumnCreator.WidthBox)
    y = ConvertToNum(ColumnCreator.LengthBox)
    z = ConvertToNum(ColumnCreator.HeightBox)

    'Detect very large values. If found, just abort the function
    If x > 99 Or y > 99 Or z > 999 Then
        Exit Function
    End If
    
    'Build collection so line images can be referenced by their index
    Set Coll = Collection_Function.BuildCollection()

    'If just changing the height (z), recompute pour window location
    If InputSource = 3 Then
        ColumnCreator.WinDim1.Value = ConvertFtIn(Round(z / 5, 0))
        ColumnCreator.WinDim2.Value = ConvertFtIn(z - ConvertToNum(ColumnCreator.WinDim1.Value))
        'GoTo UpdatePlyColorCheck
    End If
            
            
    'Clear visuals
    'Window dimensions are handled separately because if they are hidden at this point they will get hidden and unhidden under normal usage, which removes focus from the dimension, this makes it difficult to type in dimensions.
    ColumnCreator.img_line_1.Visible = False
    ColumnCreator.img_line_2.Visible = False
    ColumnCreator.img_line_3.Visible = False
    ColumnCreator.img_line_win.Visible = False
    For i = 1 To Coll.Count
        Coll.Item(i).Visible = False
    Next i
    
    'Triggers only when x, y, and z are all provided
    If Round(x * y * z, 3) <> 0 Then
    
        'Check that x, y, and z inputs are within a valid range. If not, hide any window dimensions and skip the rest of this function. (qtyCheck = 0 means the quantity box is not checked)
        If CheckInputs(ConvertToNum(ColumnCreator.WidthBox.Value), ConvertToNum(ColumnCreator.LengthBox.Value), ConvertToNum(ColumnCreator.HeightBox.Value), ConvertToNum(ColumnCreator.QuantityBox.Value), 0) = 0 Then
            ColumnCreator.WinDim1.Visible = False
            ColumnCreator.WinDim2.Visible = False
            GoTo UpdatePlyLastLine
        End If
    
        'Enable drawing buttons (may be disabled later if ply seams are invalid)
        Call EnableDrawingButtons
        
'===============================================================================================================================
'   Manage userform objects and ply_seams textbox
'===============================================================================================================================

        'Get plywood seams layout
        Dim ply_seams() As Double
        Dim temp_ht As Double: temp_ht = 0
        
        If InputSource = 3 Or ColumnCreator.boxPlySeams.Value = "" Then
            'Generate the ply seams
            ply_seams = GetPlySeams(x, y, z)
            
            'Hide any previous error messages because these fresh ply seams should be flawless
            ColumnCreator.txtPlyError.Visible = False
        ElseIf InputSource = 0 Or InputSource = 1 Or InputSource = 2 Then
            'Read the ply seams
            ply_seams = ReadSizes(ColumnCreator.boxPlySeams.Value)
            
            'If ply seams are invalid: disable the drawing buttons, hide window dimensions, and skip the rest of this function
            If ValidatePlySeams(ply_seams, x, y, z) <> 1 Then
                Call DisableDrawingButtons
                ColumnCreator.WinDim1.Visible = False
                ColumnCreator.WinDim2.Visible = False
                GoTo UpdatePlyLastLine
            End If
            

        End If
        
        'If quantity is missing, disable drawing buttons and continue
        If ConvertToNum(ColumnCreator.QuantityBox.Value) = 0 Then
            Call DisableDrawingButtons
        End If
            
        'Populate the textbox with a new plywood layout
        If InputSource = 0 Or InputSource = 3 Then  '  Or InputSource = 2
            'If input is from the x or y box and there's already a ply layout, don't replace it
            If InputSource = 0 And ColumnCreator.boxPlySeams.Value <> "" Then
                GoTo SkipPlyUpdate
            End If
            
            Dim strPlySeams As String
            For i = 1 To UBound(ply_seams)
                If i <> UBound(ply_seams) Then
                    strPlySeams = strPlySeams & ConvertFtIn(ply_seams(i)) & ", "
                ElseIf i = UBound(ply_seams) Then
                    strPlySeams = strPlySeams & ConvertFtIn(ply_seams(i))
                End If
            Next i
            ColumnCreator.boxPlySeams.Value = strPlySeams
        End If
SkipPlyUpdate:

'===============================================================================================================================
'   Draw the column on the userform
'===============================================================================================================================
        'Define origin point for column sketch
        Dim pt_draw(0 To 2) As Double
        pt_draw(0) = 200
        pt_draw(1) = 216
        pt_draw(2) = 0
        
        'Define max pixel height and actual pixel width for x and y sides
        Dim px_z_max As Double
        Dim px_x As Double
        Dim px_y As Double
        px_z_max = 200
        px_x = px_z_max * (x / z)
        px_y = px_z_max * (y / z)
        
        'Change how this is defined for view types later
        If ColumnCreator.lblAxis.Caption = "X" Then
            px_width = px_x
        ElseIf ColumnCreator.lblAxis.Caption = "Y" Then
            px_width = px_y
        Else
            MsgBox ("Error: Horizontal dimension not x or y")
        End If
        
        'Draw "frame" of column: left, right, and top
        'Left
        ColumnCreator.img_line_1.Left = pt_draw(0) - px_width / 2
        ColumnCreator.img_line_1.top = pt_draw(1) - px_z_max
        ColumnCreator.img_line_1.Width = 2
        ColumnCreator.img_line_1.Height = px_z_max
        ColumnCreator.img_line_1.Visible = True
    
        'Right
        ColumnCreator.img_line_2.Left = pt_draw(0) + px_width / 2
        ColumnCreator.img_line_2.top = pt_draw(1) - px_z_max
        ColumnCreator.img_line_2.Width = 2
        ColumnCreator.img_line_2.Height = px_z_max
        ColumnCreator.img_line_2.Visible = True
    
        'Top
        ColumnCreator.img_line_3.Left = pt_draw(0) - px_width / 2
        ColumnCreator.img_line_3.top = pt_draw(1) - px_z_max
        ColumnCreator.img_line_3.Width = px_width
        ColumnCreator.img_line_3.Height = 2
        ColumnCreator.img_line_3.Visible = True
        
        'Draw plywood seams
        Dim cumulative_z As Double
        For i = 1 To UBound(ply_seams) - 1
            Coll(i).Left = pt_draw(0) - px_width / 2
            cumulative_z = 0
            For j = 1 To i
                cumulative_z = cumulative_z + ply_seams(j)
            Next j
            Coll(i).top = pt_draw(1) - px_z_max * (cumulative_z / z)
            Coll(i).Width = px_width
            Coll(i).Height = 2
            Coll(i).Visible = True
        Next i
        
        'Dimension plywood seams
        For i = 1 To UBound(ply_seams)
            Coll(i + 10).Left = pt_draw(0) + px_width / 2 + 10
            cumulative_z = 0
            For j = 1 To i
                cumulative_z = cumulative_z + ply_seams(j)
            Next j
            Coll(i + 10).top = pt_draw(1) - px_z_max * ((cumulative_z - ply_seams(i) / 2) / z) - Coll(i + 10).Height / 2 + 2
            Coll(i + 10).Caption = ConvertFtIn(ply_seams(i))
            Coll(i + 10).Visible = True
        Next i
        
        'Create window seam
        If ColumnCreator.chkWinX.Value = True Or ColumnCreator.chkWinY.Value = True Then
            'Create values for window positions if first time
            If ColumnCreator.WinDim1.Value = "Z1" Then
                ColumnCreator.WinDim1.Value = ConvertFtIn(Round(z / 5, 0)) 'Just assume window is top 1/4 of column for starters
                ColumnCreator.WinDim2.Value = ConvertFtIn(z - ConvertToNum(ColumnCreator.WinDim1.Value))
            End If
            
            'Catch pour window dimensions that go off screen, change to max height
            If InputSource = 2 Then
                If ConvertToNum(ColumnCreator.WinDim1.Value) > z Then
                    ColumnCreator.WinDim1.Value = ConvertFtIn(z)
                    ColumnCreator.WinDim2.Value = ConvertFtIn(0)
                ElseIf ConvertToNum(ColumnCreator.WinDim2.Value) > z Then
                    ColumnCreator.WinDim2.Value = ConvertFtIn(z)
                    ColumnCreator.WinDim1.Value = ConvertFtIn(0)
                End If
            End If
            
            If InputSource = 0 Or InputSource = 2 Or InputSource = 3 Then
                'Set location of window seam
                ColumnCreator.img_line_win.Left = pt_draw(0) - px_width / 2
                ColumnCreator.img_line_win.top = pt_draw(1) - px_z_max + ConvertToNum(ColumnCreator.WinDim1.Value) * px_z_max / z
                ColumnCreator.img_line_win.Width = px_width
                ColumnCreator.img_line_win.Height = 3 'Thicc
                
                'Move dimensions into place (upper dim)
                ColumnCreator.WinDim1.Left = pt_draw(0) - px_width / 2 - 40
                ColumnCreator.WinDim1.top = pt_draw(1) - px_z_max + (ConvertToNum(ColumnCreator.WinDim1.Value) * px_z_max / z) / 2 - ColumnCreator.WinDim1.Height / 2
                'Move dimensions into place (lower dim)
                ColumnCreator.WinDim2.Left = pt_draw(0) - px_width / 2 - 40
                ColumnCreator.WinDim2.top = pt_draw(1) - (ConvertToNum(ColumnCreator.WinDim2.Value) * px_z_max / z) / 2 - ColumnCreator.WinDim1.Height / 2
                
                'If the window positioning dimensions add up to the height, make the dimensions blue, otherwise, grey
UpdatePlyColorCheck:
                If Round(ConvertToNum(ColumnCreator.WinDim1.Value) + ConvertToNum(ColumnCreator.WinDim2.Value), 5) = Round(z, 5) Then
                    ColumnCreator.WinDim1.ForeColor = &HFF0000
                    ColumnCreator.WinDim2.ForeColor = &HFF0000
                Else
                    ColumnCreator.WinDim1.ForeColor = &H80000011
                    ColumnCreator.WinDim2.ForeColor = &H80000011
                End If
            
            End If

            'Make window seam and dimensions visible
            ColumnCreator.img_line_win.Visible = True
            ColumnCreator.WinDim1.Visible = True
            ColumnCreator.WinDim2.Visible = True
        Else
            'Hide window dimensions if no window option is checked
            ColumnCreator.WinDim1.Visible = False
            ColumnCreator.WinDim2.Visible = False
        End If
    Else
        'Hide window dimensions if missing inputs
        ColumnCreator.WinDim1.Visible = False
        ColumnCreator.WinDim2.Visible = False
    End If
    
UpdatePlyLastLine:
End Function

'===============================================================================================================================
'   Other useful functions
'===============================================================================================================================

Public Function DisableDrawingButtons()
    'Disable drawing buttons
    ColumnCreator.CommandButton1.Enabled = False
    ColumnCreator.CommandButton1.BackColor = &H80000004 'grey
    ColumnCreator.CommandButton1.ForeColor = &H80000000 'background grey
    ColumnCreator.CommandButton1.Enabled = False
    ColumnCreator.CommandButton1.BackColor = &H80000004 'grey
    ColumnCreator.CommandButton1.ForeColor = &H80000000 'background grey
End Function
Public Function EnableDrawingButtons()
    'Enable drawing buttons
    ColumnCreator.CommandButton1.Enabled = True
    ColumnCreator.CommandButton1.BackColor = &H8000000D 'blue
    ColumnCreator.CommandButton1.ForeColor = &H80000012 'black
    ColumnCreator.CommandButton1.Enabled = True
    ColumnCreator.CommandButton1.BackColor = &H8000000D 'blue
    ColumnCreator.CommandButton1.ForeColor = &H80000012 'black
End Function
Public Function ValidatePlySeams(ply_seams() As Double, x As Double, y As Double, z As Double) As Integer
'Returns 0: not valid
'Returns 1: valid
    
    'Assume layout is valid
    ValidatePlySeams = 1
    
    'Check whether the sum of listed lengths equals the column height
    Dim temp_ht As Double: temp_ht = 0
    For i = 1 To UBound(ply_seams)
        temp_ht = temp_ht + ply_seams(i)
    Next i
    If Round(temp_ht, 3) <> Round(z, 3) Then
        If temp_ht > z Then
            ColumnCreator.txtPlyError.Caption = "Remove " & ConvertFtIn(temp_ht - z)
        ElseIf temp_ht < z Then
            ColumnCreator.txtPlyError.Caption = "Add " & ConvertFtIn(z - temp_ht)
        End If
        ColumnCreator.txtPlyError.Visible = True
        ValidatePlySeams = 0
        Call DisableDrawingButtons
        GoTo ValidatePlySeamsLastLine
    End If
    
    'Check that plywood doesn't exceed max size
    Dim ply_width_x As Double
    Dim ply_width_y As Double
    Dim min_ply_ht As Double: min_ply_ht = 6
    Dim max_ply_ht As Double
    
    ply_width_x = x + 1.5
    ply_width_y = y + 1.5
    If Round(ply_width_x, 3) > 48 Or Round(ply_width_y, 3) > 48 Then
        max_ply_ht = 48
    Else
        max_ply_ht = 96
    End If
    
    For i = 1 To UBound(ply_seams)
        If ply_seams(i) > max_ply_ht Then
            ColumnCreator.txtPlyError.Caption = ConvertFtIn(ply_seams(i)) & " ply too tall. Max: " & ConvertFtIn(max_ply_ht)
            ColumnCreator.txtPlyError.Visible = True
            ValidatePlySeams = 0
            Call DisableDrawingButtons
            GoTo ValidatePlySeamsLastLine
        ElseIf ply_seams(i) < min_ply_ht Then
            ColumnCreator.txtPlyError.Caption = ConvertFtIn(ply_seams(i)) & " ply too small. Min: " & ConvertFtIn(min_ply_ht)
            ColumnCreator.txtPlyError.Visible = True
            ValidatePlySeams = 0
            Call DisableDrawingButtons
            GoTo ValidatePlySeamsLastLine
        Else
            ColumnCreator.txtPlyError.Visible = False
        End If
    Next i

'Hide error text if no errors have been found here
If ValidatePlySeams = 1 Then
    ColumnCreator.txtPlyError.Visible = False
End If

ValidatePlySeamsLastLine:
End Function

Attribute VB_Name = "sUpdatePly"
Public Function sUpdatePly(InputSource As Integer)

' # # # # # # # # # # # # # # # # # # # # # # # # # # # #
'              FOR SCISSOR CLAMP COLUMNS
' # # # # # # # # # # # # # # # # # # # # # # # # # # # #

    'Input source of 0 is for changes from the x, y, and z boxes or from changing the axis
    'Input source of 1 is for changes from boxPlySeams
    'Input source of 2 is for changes from the window checkboxes or the window position dimensions (INVALID FOR SCISSOR CLAMPS)
    'Input source of 3 is for changes from the z box only

    Dim x As Double
    Dim y As Double
    Dim z As Double
    
    x = ConvertToNum(ColumnCreator.sWidthBox)
    y = ConvertToNum(ColumnCreator.sLengthBox)
    z = ConvertToNum(ColumnCreator.sHeightBox)
    
    'Detect very large values. If found, just abort the function
    If x > 99 Or y > 99 Or z > 528 Then
        Exit Function
    End If
    
    'Build collection so line images can be referenced by their index
    Set Coll = Collection_Function.BuildCollection()
            
    'Clear visuals
    'Window dimensions are handled separately because if they are hidden at this point they will get hidden and unhidden under normal usage, which removes focus from the dimension, this makes it difficult to type in dimensions.
    ColumnCreator.s_img_line_1.Visible = False
    ColumnCreator.s_img_line_2.Visible = False
    ColumnCreator.s_img_line_3.Visible = False
    For i = 1 To Coll.Count
        Coll.Item(i).Visible = False
    Next i
    
    'Triggers only when x, y, and z are all provided
    If Round(x * y * z, 3) <> 0 Then
    
        'Check that x, y, and z inputs are valid. If not, skip the rest of this function. (qtyCheck = 0 means the quantity box is not considered)
        If CheckInputs(ConvertToNum(ColumnCreator.sWidthBox.Value), ConvertToNum(ColumnCreator.sLengthBox.Value), ConvertToNum(ColumnCreator.sHeightBox.Value), ConvertToNum(ColumnCreator.sQuantityBox.Value), 0) = 0 Then
            Call sDisableDrawingButtons
            GoTo UpdatePlyLastLine
        End If
    
        'Enable drawing buttons (may be disabled later if ply seams are invalid)
        Call sEnableDrawingButtons
        
'===============================================================================================================================
'   Manage userform objects and ply_seams textbox
'===============================================================================================================================

        'Get plywood seams layout
        Dim ply_seams() As Double
        Dim temp_ht As Double: temp_ht = 0

        If InputSource = 3 Or ColumnCreator.sboxPlySeams.Value = "" Then
            'Generate the ply seams
            ply_seams = GetPlySeams(x, y, z)
            
            'Hide any previous error messages because these fresh ply seams should be flawless
            ColumnCreator.stxtPlyError.Visible = False
        ElseIf InputSource = 0 Or InputSource = 1 Then
            'Read the ply seams
            ply_seams = ReadSizes(ColumnCreator.sboxPlySeams.Value)
            
            'If ply seams are invalid: disable the drawing buttons and skip the rest of this function
            If sValidatePlySeams(ply_seams, x, y, z) <> 1 Then
                Call sDisableDrawingButtons
                GoTo UpdatePlyLastLine
            End If
        End If
        
        'If quantity is missing, disable drawing buttons and continue
        If ConvertToNum(ColumnCreator.sQuantityBox.Value) = 0 Then
            Call sDisableDrawingButtons
        End If
            
        'Populate the textbox with a new plywood layout
        If InputSource = 0 Or InputSource = 3 Then
            'If input is from the x or y box and there's already a ply layout, don't replace it
            If InputSource = 0 And ColumnCreator.sboxPlySeams.Value <> "" Then
                GoTo SkipPlyUpdate
            End If
            
            Dim strPlySeams As String
            For i = 1 To UBound(ply_seams)
                If i <> UBound(ply_seams) Then
                    strPlySeams = strPlySeams & ConvertFtIn(ply_seams(i)) & ", "
                ElseIf i = UBound(ply_seams) Then
                    strPlySeams = strPlySeams & ConvertFtIn(ply_seams(i))
                End If
            Next i
            ColumnCreator.sboxPlySeams.Value = strPlySeams
        End If
SkipPlyUpdate:

'===============================================================================================================================
'   Draw the column on the userform
'===============================================================================================================================
        'Define origin point for column sketch
        Dim pt_draw(0 To 2) As Double
        pt_draw(0) = 200
        pt_draw(1) = 216
        pt_draw(2) = 0
        
        'Define max pixel height and actual pixel width for x and y sides
        Dim px_z_max As Double
        Dim px_x As Double
        Dim px_y As Double
        If z > 96 Then 'Display column at full height and modify the width to scale
            px_z_max = 200
            px_x = px_z_max * (x / z)
            px_y = px_z_max * (y / z)
        Else 'Scale down display height and width to fit. Without this step, a short column will be displayed as extremely wide and go off screen.
            px_z_max = 200 * z / 96
            px_x = px_z_max * (x / z) * z / 96
            px_y = px_z_max * (y / z) * z / 96
        End If
        
        'Change how this is defined for view types later
        If ColumnCreator.slblAxis.Caption = "X" Then
            px_width = px_x
        ElseIf ColumnCreator.slblAxis.Caption = "Y" Then
            px_width = px_y
        Else
            MsgBox ("Error: Horizontal dimension not x or y")
        End If
        
        'Draw "frame" of column: left, right, and top
        'Left
        ColumnCreator.s_img_line_1.Left = pt_draw(0) - px_width / 2
        ColumnCreator.s_img_line_1.top = pt_draw(1) - px_z_max
        ColumnCreator.s_img_line_1.Width = 2
        ColumnCreator.s_img_line_1.Height = px_z_max
        ColumnCreator.s_img_line_1.Visible = True
    
        'Right
        ColumnCreator.s_img_line_2.Left = pt_draw(0) + px_width / 2
        ColumnCreator.s_img_line_2.top = pt_draw(1) - px_z_max
        ColumnCreator.s_img_line_2.Width = 2
        ColumnCreator.s_img_line_2.Height = px_z_max
        ColumnCreator.s_img_line_2.Visible = True
    
        'Top
        ColumnCreator.s_img_line_3.Left = pt_draw(0) - px_width / 2
        ColumnCreator.s_img_line_3.top = pt_draw(1) - px_z_max
        ColumnCreator.s_img_line_3.Width = px_width
        ColumnCreator.s_img_line_3.Height = 2
        ColumnCreator.s_img_line_3.Visible = True
        
        'Draw plywood seams
        Dim cumulative_z As Double
        For i = 1 To UBound(ply_seams) - 1
            Coll(i).Left = pt_draw(0) - px_width / 2
            cumulative_z = 0
            For j = 1 To i
                cumulative_z = cumulative_z + ply_seams(j)
            Next j
            Coll(i).top = pt_draw(1) - px_z_max * (cumulative_z / z)
            Coll(i).Width = px_width
            Coll(i).Height = 2
            Coll(i).Visible = True
        Next i
        
        'Dimension plywood seams
        For i = 1 To UBound(ply_seams)
            Coll(i + 10).Left = pt_draw(0) + px_width / 2 + 10
            cumulative_z = 0
            For j = 1 To i
                cumulative_z = cumulative_z + ply_seams(j)
            Next j
            Coll(i + 10).top = pt_draw(1) - px_z_max * ((cumulative_z - ply_seams(i) / 2) / z) - Coll(i + 10).Height / 2 + 2
            Coll(i + 10).Caption = ConvertFtIn(ply_seams(i))
            Coll(i + 10).Visible = True
        Next i
    End If
    
UpdatePlyLastLine:
End Function

'===============================================================================================================================
'   Other useful functions
'===============================================================================================================================

Public Function sDisableDrawingButtons()
    'Disable drawing buttons
    ColumnCreator.CommandButton2.Enabled = False
    ColumnCreator.CommandButton2.BackColor = &H80000004 'grey
    ColumnCreator.CommandButton2.ForeColor = &H80000000 'background grey
    ColumnCreator.CommandButton2.Enabled = False
    ColumnCreator.CommandButton2.BackColor = &H80000004 'grey
    ColumnCreator.CommandButton2.ForeColor = &H80000000 'background grey
End Function
Public Function sEnableDrawingButtons()
    'Enable drawing buttons
    ColumnCreator.CommandButton2.Enabled = True
    ColumnCreator.CommandButton2.BackColor = &H8000000D  'blue
    ColumnCreator.CommandButton2.ForeColor = &H80000012  'black
    ColumnCreator.CommandButton2.Enabled = True
    ColumnCreator.CommandButton2.BackColor = &H8000000D  'blue
    ColumnCreator.CommandButton2.ForeColor = &H80000012  'black
End Function
Public Function sValidatePlySeams(ply_seams() As Double, x As Double, y As Double, z As Double) As Integer
'Returns 0: not valid
'Returns 1: valid
    
    'Assume layout is valid
    sValidatePlySeams = 1
    
    'Check whether the sum of listed lengths equals the column height
    Dim temp_ht As Double: temp_ht = 0
    For i = 1 To UBound(ply_seams)
        temp_ht = temp_ht + ply_seams(i)
    Next i
    If Round(temp_ht, 3) <> Round(z, 3) Then
        If temp_ht > z Then
            ColumnCreator.stxtPlyError.Caption = "Remove " & ConvertFtIn(temp_ht - z)
        ElseIf temp_ht < z Then
            ColumnCreator.stxtPlyError.Caption = "Add " & ConvertFtIn(z - temp_ht)
        End If
        ColumnCreator.stxtPlyError.Visible = True
        sValidatePlySeams = 0
        GoTo sValidatePlySeamsLastLine
    End If
    
    'Check that plywood doesn't exceed max size
    Dim ply_width_x As Double
    Dim ply_width_y As Double
    Dim min_ply_ht As Double: min_ply_ht = 6
    Dim max_ply_ht As Double
    
    ply_width_x = x
    ply_width_y = y + 4.5
    If Round(ply_width_x, 3) > 48 Or Round(ply_width_y, 3) > 48 Then
        max_ply_ht = 48
    Else
        max_ply_ht = 96
    End If
    
    For i = 1 To UBound(ply_seams)
        If ply_seams(i) > max_ply_ht Then
            ColumnCreator.stxtPlyError.Caption = ConvertFtIn(ply_seams(i)) & " ply too tall. Max: " & ConvertFtIn(max_ply_ht)
            ColumnCreator.stxtPlyError.Visible = True
            sValidatePlySeams = 0
            GoTo sValidatePlySeamsLastLine
        ElseIf ply_seams(i) < min_ply_ht Then
            ColumnCreator.stxtPlyError.Caption = ConvertFtIn(ply_seams(i)) & " ply too small. Min: " & ConvertFtIn(min_ply_ht)
            ColumnCreator.stxtPlyError.Visible = True
            sValidatePlySeams = 0
            GoTo sValidatePlySeamsLastLine
        Else
            ColumnCreator.stxtPlyError.Visible = False
        End If
    Next i

'Hide error text if no errors have been found here
If sValidatePlySeams = 1 Then
    ColumnCreator.stxtPlyError.Visible = False
End If

sValidatePlySeamsLastLine:
End Function

Public Function sCheckHeight(x As Double, y As Double, z As Double)
    
    Dim big_dim As Double
    Dim max_ht As Double
    
    'Check that x, and y are provided. If either are missing, hide the max height text and don't do this function
    'The max height text is also hidden from the CheckInputs_Function
    If x = 0 Or y = 0 Then
        ColumnCreator.slblMaxHt.Caption = "N/A"
        Exit Function
    End If
    
    'Find the longer side of the column
    If x >= y Then
        big_dim = x
    Else
        big_dim = y
    End If
    
    'Use a pre-built table to set the maximum height
    Select Case Round(big_dim, 3)
    Case Is <= 8
        max_ht = 196
    Case Is <= 10
        max_ht = 196
    Case Is <= 12
        max_ht = 196
    Case Is <= 14
        max_ht = 196
    Case Is <= 16
        max_ht = 196
    Case Is <= 18
        max_ht = 197
    Case Is <= 20
        max_ht = 197
    Case Is <= 22
        max_ht = 193
    Case Is <= 24
        max_ht = 195
    Case Is <= 26
        max_ht = 175
    Case Is <= 28
        max_ht = 175
    Case Is <= 30
        max_ht = 175
    Case Is <= 32
        max_ht = 133
    Case Is <= 34
        max_ht = 133
    Case Is <= 36
        max_ht = 180
    Case Is <= 38
        max_ht = 127
    Case Is <= 40
        max_ht = 127
    Case Is <= 42
        max_ht = 127
    Case Is <= 44
        max_ht = 127
    Case Is <= 46
        max_ht = 127
    End Select

    'Display the max height on the userform
    ColumnCreator.slblMaxHt.Caption = ConvertFtIn(max_ht)
    
    'Run check inputs
    Call CheckInputs(ConvertToNum(ColumnCreator.sWidthBox.Value), ConvertToNum(ColumnCreator.sLengthBox.Value), ConvertToNum(ColumnCreator.sHeightBox.Value), ConvertToNum(ColumnCreator.sQuantityBox.Value), 1)
    
End Function

Attribute VB_Name = "zScissorClampModule"
Public Function CreateScissorClamp()
    'Use error handler
    On Error GoTo ErrorHandler
    
    ColumnCreator.Hide 'Hide GUI form after clicking this command button
    
    'Referenced files are found within this folder, easier to change this partial path
    Dim FileLocationPrefix As String
    Dim filepath As String
    
    'FileLocationPrefix = "Z:\Shared\NCA\Users\Quincy\VBA\"
    FileLocationPrefix = "D:\Rider projects\ColumnDesign\ColumnDesign\Source\"
    filepath = FileLocationPrefix & "Columns\scissor_clamp_matrix.csv"
    
    'Define layers, assign colors, assign linetypes
    Dim LayerObj As AcadLayer 'Creates layer object
    Dim color As AcadAcCmColor
    Dim version As String
    Dim col_ver_str As String
    On Error Resume Next
        version = ThisDrawing.Application.version
        version = Mid(version, 1, 2) 'Records the first 2 characters in the string as the version number
        col_ver_str = "AutoCAD.AcCmColor." & version
        Set color = AcadApplication.GetInterfaceObject(col_ver_str) 'Use version number to set color object

        color.ColorIndex = 154:     Set LayerObj = ThisDrawing.Layers.Add("DIM"):       LayerObj.TrueColor = color:    LayerObj.Linetype = "Continuous"
        color.ColorIndex = acRed:   Set LayerObj = ThisDrawing.Layers.Add("ELEV"):      LayerObj.TrueColor = color:    LayerObj.Linetype = "Continuous"
        color.ColorIndex = acCyan:  Set LayerObj = ThisDrawing.Layers.Add("FMTEXTA"):   LayerObj.TrueColor = color:    LayerObj.Linetype = "Continuous"
        color.ColorIndex = acBlue:  Set LayerObj = ThisDrawing.Layers.Add("FORM"):      LayerObj.TrueColor = color:    LayerObj.Linetype = "Continuous"
        color.ColorIndex = acBlue:  Set LayerObj = ThisDrawing.Layers.Add("NOTES"):     LayerObj.TrueColor = color:    LayerObj.Linetype = "Continuous"
        color.ColorIndex = acCyan:  Set LayerObj = ThisDrawing.Layers.Add("PLYA"):      LayerObj.TrueColor = color:    LayerObj.Linetype = "Continuous"
        color.ColorIndex = 23:      Set LayerObj = ThisDrawing.Layers.Add("SHADE"):     LayerObj.TrueColor = color:    LayerObj.Linetype = "Continuous"
        color.ColorIndex = acBlue:  Set LayerObj = ThisDrawing.Layers.Add("STEEL"):     LayerObj.TrueColor = color:    LayerObj.Linetype = "Continuous"
    On Error GoTo ErrorHandler
    
    'Check if any of the used layers are locked, remember which are locked, then unlock them
    Dim UsedLayerList(1 To 8) As String ' fill with used layers
    Dim LockedLayerList(1 To 8) As Integer 'leave at default values of 0, change to 1 for locked layers
    Dim FrozenLayerList(1 To 8) As Integer 'leave at default values of 0, change to 1 for frozen layers
    Dim InvisLayerList(1 To 8) As Integer 'leave at default values of 0, change to 1 for invisible layers
    UsedLayerList(1) = "DIM": UsedLayerList(2) = "ELEV": UsedLayerList(3) = "FMTEXTA": UsedLayerList(4) = "FORM": UsedLayerList(5) = "NOTES":
    UsedLayerList(6) = "PLYA": UsedLayerList(7) = "SHADE": UsedLayerList(8) = "STEEL":

    For i = 1 To UBound(UsedLayerList)
        Set LayerObj = ThisDrawing.Layers(UsedLayerList(i))
        If LayerObj.Lock = True Then
            LayerObj.Lock = False
            LockedLayerList(i) = 1
        End If
        If LayerObj.Freeze = True Then
            LayerObj.Freeze = False
            FrozenLayerList(i) = 1
        End If
        If LayerObj.LayerOn = False Then
            InvisLayerList(i) = 1
        End If
    Next i
    
    'Make new dim style, text style, and layers
    Dim OldDimStyle As AcadDimStyle
    Dim OldTextStyle As AcadTextStyle
    Dim OldLayer As AcadLayer
    
    Set OldDimStyle = ThisDrawing.ActiveDimStyle
    Set OldTextStyle = ThisDrawing.ActiveTextStyle
    Set OldLayer = ThisDrawing.ActiveLayer
    
    Call BuildColumnStyles

    'Define various column parameters
    Dim x As Double
    Dim y As Double
    Dim z As Double
    Dim n_col As Integer
    Dim n_studs_x As Integer 'Number of studs on the "x" side
    Dim n_studs_y As Integer 'Number of studs on the "y" side
    Dim n_clamps As Integer: n_clamps = 0 'Total number of clamps on column
    Dim n_clamps_temp As Integer: n_clamps_temp = 0 'Number of clamps for one pour lift
    Dim stud_type As Integer 'Stud types: 1 = 2x4,  2 = LVL
    Dim clamp_size As Integer 'Clamp sizes: 4 = 36",  5 = 48",  6 = 60"
    Dim col_wt As Integer
    Dim ply_name As String
    Dim stud_name As String
    Dim stud_name_full As String 'A more elaborate name to include LVL dimensions
    Dim stud_block As String
    Dim stud_block_spax As String
    Dim stud_block_bolt As String
    Dim stud_face_block As String

    'Other definitions
    Dim ply_thk As Double: ply_thk = 0.75
    Dim stud_base_gap As Double: stud_base_gap = 0.25 'Gap between bottom of stud and ground
    Dim bot_clamp_gap As Double: bot_clamp_gap = 6 'space between the bottom clamp and the ground.
    Dim stud_start_offset_x As Double: stud_start_offset_x = 0.125 'Distance from edge of ply to outermost stud on short panel
    Dim stud_start_offset_y As Double: stud_start_offset_y = 2.375 'Distance from edge of ply to outermost stud on long panel
    pi = 4 * Atn(1)
    
    'Assign input box values to variables
    x = ConvertToNum(ColumnCreator.sWidthBox)
    y = ConvertToNum(ColumnCreator.sLengthBox)
    z = ConvertToNum(ColumnCreator.sHeightBox)
    n_col = ConvertToNum(ColumnCreator.sQuantityBox)
    ply_name = ColumnCreator.sPlyNameBox

    'Assign stud type (always use 2x4s)
    stud_type = 1
    stud_name = "2X4"
    stud_name_full = "2X4"
    stud_block = "VBA_2X4": stud_block_spax = "VBA_2X4_SPAX": stud_block_bolt = "VBA_2X4_BOLT"
    stud_face_block = "VBA_2X4_FACE"
    
    'Assign x and y values to array
    Dim Arr(2) As Double: Arr(0) = x: Arr(1) = y
    
    'x: Add 0 inches to nominal width for ply sheet width on the short side
    'y: Add 4.5 inches to nominal width for ply sheet width on the long side
    Dim ply_width_x As Double
    Dim ply_width_y As Double
    ply_width_x = x
    ply_width_y = y + 4.5
        
        
    'If library block is missing: load VBA_Block_Library .dwg file as a block to load all needed blocks, then delete that file block
    Dim BlockExists As Boolean
    BlockExists = False

    'Check if library was loaded:
    For Each entry In ActiveDocument.Blocks
        If entry.Name = "VBA_SHIBBOLETH" Then
            BlockExists = True
            Exit For
        End If
    Next
    
    Dim insertionPnt(0 To 2) As Double
    insertionPnt(0) = 0#: insertionPnt(1) = 0#: insertionPnt(2) = 0#
    FileToInsert = FileLocationPrefix & "VBA_Block_Library.dwg"
    If BlockExists = False Then
        Dim BlockDwg As AcadBlockReference
        Set BlockDwg = ThisDrawing.ModelSpace.InsertBlock(insertionPnt, FileToInsert, 1#, 1#, 1#, 0)
        BlockDwg.Delete
    End If


'#####################################################################################
'                                     S T U D S
'#####################################################################################
    'Compute number of studs required for each side
    Dim row_num As Integer: row_num = 0 'height
    Dim col_num_x As Integer: col_num_x = 0 'x
    Dim col_num_y As Integer: col_num_y = 0 'y
    Dim n_studs_total As Integer 'Total studs on all sides
    
    'Create stud_matrix, number of studs used for each column size (column height doesn't matter)
    Dim stud_matrix(1 To 20, 1 To 2) As Integer
    stud_matrix(1, 1) = 8:     stud_matrix(1, 2) = 2
    stud_matrix(2, 1) = 10:     stud_matrix(2, 2) = 2
    stud_matrix(3, 1) = 12:     stud_matrix(3, 2) = 2
    stud_matrix(4, 1) = 14:     stud_matrix(4, 2) = 3
    stud_matrix(5, 1) = 16:     stud_matrix(5, 2) = 3
    stud_matrix(6, 1) = 18:     stud_matrix(6, 2) = 3
    stud_matrix(7, 1) = 20:     stud_matrix(7, 2) = 3
    stud_matrix(8, 1) = 22:     stud_matrix(8, 2) = 4
    stud_matrix(9, 1) = 24:     stud_matrix(9, 2) = 4
    stud_matrix(10, 1) = 26:     stud_matrix(10, 2) = 4
    stud_matrix(11, 1) = 28:     stud_matrix(11, 2) = 4
    stud_matrix(12, 1) = 30:     stud_matrix(12, 2) = 5
    stud_matrix(13, 1) = 32:     stud_matrix(13, 2) = 5
    stud_matrix(14, 1) = 34:    stud_matrix(14, 2) = 5
    stud_matrix(15, 1) = 36:    stud_matrix(15, 2) = 5
    stud_matrix(16, 1) = 38:    stud_matrix(16, 2) = 5
    stud_matrix(17, 1) = 40:    stud_matrix(17, 2) = 6
    stud_matrix(18, 1) = 42:    stud_matrix(18, 2) = 6
    stud_matrix(19, 1) = 44:    stud_matrix(19, 2) = 6
    stud_matrix(20, 1) = 46:    stud_matrix(20, 2) = 6

    'Find number of studs for each side
    'Number of x studs
    For i = 1 To UBound(stud_matrix, 1)
        If Round(stud_matrix(i, 1), 3) >= Round(x, 3) Then
            n_studs_x = stud_matrix(i, 2)
            Exit For
        End If
    Next i
    
    'Number of y studs
    For i = 1 To UBound(stud_matrix, 1)
        If Round(stud_matrix(i, 1), 3) >= Round(y, 3) Then
            n_studs_y = stud_matrix(i, 2)
            Exit For
        End If
    Next i
    
    'Calculate total number of studs
    n_studs_total = n_studs_x * 2 + n_studs_y * 2
    
    'Compute stud spacing/locations assuming equal spacing
    Dim stud_spacing_x() As Double
    Dim stud_spacing_y() As Double
    ReDim stud_spacing_x(1 To n_studs_x)
    ReDim stud_spacing_y(1 To n_studs_y)

    For i = 1 To n_studs_x
        stud_spacing_x(i) = stud_start_offset_x + (i - 1) * (ply_width_x - 2 * stud_start_offset_x - 3.5) / (n_studs_x - 1)
    Next i
    For i = 1 To n_studs_y
        stud_spacing_y(i) = stud_start_offset_y + (i - 1) * (ply_width_y - 2 * stud_start_offset_y - 3.5) / (n_studs_y - 1)
    Next i
    


'#####################################################################################
'                                   P L Y W O O D
'#####################################################################################
    Dim ply_top_ht_min As Double: ply_top_ht_min = 6 'Smallest allowable strip of plywood at top of column
    Dim max_ply_ht As Double
    Dim ply_seams() As Double '1 dimensional matrix that stores vertical length of each ply piece. First entry is bottom plywood.

    'Read plywood seams from the userform
    ply_seams = ReadSizes(ColumnCreator.sboxPlySeams.Value)

    'Re-validate the ply seams if somehow they have an issue
    If sUpdatePly.sValidatePlySeams(ply_seams, x, y, z) = 0 Then
        MsgBox ("Error: Plywood layout invalid. You should never see this message...How did you do this?")
        GoTo last_line
    End If
    
    'Assign x or y information to the elevation view so it can easily be referenced
    Dim n_studs_e As Integer
    Dim ply_width_e As Double
    Dim stud_spacing_e() As Double
    
    'Aassume elevation view will display side x
    n_studs_e = n_studs_x
    ply_width_e = ply_width_x
    ReDim stud_spacing_e(1 To UBound(stud_spacing_x))
    For i = 1 To UBound(stud_spacing_x)
        stud_spacing_e(i) = stud_spacing_x(i)
    Next i
    
    'If column is very wide, use rotated sheets and thus 48" max height
    If Round(ply_width_x, 3) > 48 Or Round(ply_width_y, 3) > 48 Then
        max_ply_ht = 48
    Else
        max_ply_ht = 96
    End If

    'Create 2D array for plywood cut counts. Columns: (width / height / quantity) 'ply_cuts(k, 1) = ply_width_x 'TRANSPOSE THIS STUPID MATRIX
    'First find number of unique sheet sizes
    Dim unique_plys As Integer
    Dim ply_widths(1 To 2) As Double
    Dim ply_cuts() As Double:   ReDim ply_cuts(1 To 3, 1 To 1) As Double    'Array for plywood sheet sizes for counts
    
    unique_plys = 0 '1 size of plywood is the bare minimum
    
    'Create array of plywood widths
    ply_widths(1) = ply_width_x
    ply_widths(2) = ply_width_y

    'For each entry in ply_seams
    For i = 1 To UBound(ply_seams)
        'For each side of the panel (A and B)
        For j = 1 To UBound(ply_widths)
            'Check if this width and height combination has been entered before, then add it to the existing entry or create an new entry
            For k = 1 To UBound(ply_cuts, 2)
                If Round(ply_cuts(1, k), 3) = Round(ply_widths(j), 3) And Round(ply_cuts(2, k), 3) = Round(ply_seams(i), 3) Then
                    ply_cuts(3, k) = ply_cuts(3, k) + 2 'Add 2 to the existing count
                    GoTo ExitPlywoodCheckLoop
                ElseIf k = UBound(ply_cuts, 2) Then
                    unique_plys = unique_plys + 1
                    ReDim Preserve ply_cuts(1 To 3, 1 To unique_plys)
                    ply_cuts(1, unique_plys) = ply_widths(j)
                    ply_cuts(2, unique_plys) = ply_seams(i)
                    ply_cuts(3, unique_plys) = ply_cuts(3, unique_plys) + 2 'Start a new count at 2
                    GoTo ExitPlywoodCheckLoop
                End If
            Next k
ExitPlywoodCheckLoop:
        Next j
    Next i

    'Remove the last line if it's 0
    If Round(ply_cuts(1, UBound(ply_cuts, 2)), 3) = 0 Then
        ReDim Preserve ply_cuts(1 To 3, 1 To UBound(ply_cuts, 2) - 1)
        unique_plys = unique_plys - 1
    End If

    Dim msg As String
    For i = 1 To UBound(ply_cuts, 2)
        For ii = 1 To UBound(ply_cuts, 1)
            msg = msg & ply_cuts(ii, i) & vbTab 'replace with space(1) if array too big
        Next ii
        msg = msg & vbCrLf
    Next i
    'MsgBox msg

    
'#####################################################################################
'                                   C L A M P S
'#####################################################################################
    'Compute clamp size. Use maximum dimension to pick clamp.
    '1 = 36",  2 = 48",  3 = 60"
    Dim clamp_spacing() As Double
    Dim n_pours As Integer 'Minimum number of pours needed to fill scissor form given full liquid head limit from clamp spacing matrix.
    
    If ColumnCreator.sClampSizeButton1.Value = True Then
        GoTo Clampsize1
    ElseIf ColumnCreator.sClampSizeButton2.Value = True Then
        GoTo Clampsize2
    ElseIf ColumnCreator.sClampSizeButton3.Value = True Then
        GoTo Clampsize3
    ElseIf ColumnCreator.sClampSizeButton4.Value = True Then
        GoTo ClampSizeChoose
    End If
    
ClampSizeChoose:
    If Round(FindMax(Arr), 3) < 23.5 Then
Clampsize1:
        clamp_size = 4
        clamp_L = 36
        clamp_width = 2.5
        clamp_name = "36"" SCISSOR CLAMP"
        clamp_block = "VBA_36_SCISSOR_CLAMP_PLAN"
        clamp_block_pr = "VBA_36_SCISSOR_CLAMP_PROFILE"
        clamp_block_pr_flip = "VBA_36_SCISSOR_CLAMP_PROFILE_FLIP"
    ElseIf Round(FindMax(Arr), 3) <= 35.5 Then
Clampsize2:
        clamp_size = 5
        clamp_L = 48
        clamp_width = 2.5
        clamp_name = "48"" SCISSOR CLAMP"
        clamp_block = "VBA_48_SCISSOR_CLAMP_PLAN"
        clamp_block_pr = "VBA_48_SCISSOR_CLAMP_PROFILE"
        clamp_block_pr_flip = "VBA_48_SCISSOR_CLAMP_PROFILE_FLIP"
    ElseIf Round(FindMax(Arr), 3) <= 46 Then
Clampsize3:
        clamp_size = 6
        clamp_L = 60
        clamp_width = 3
        clamp_name = "60"" SCISSOR CLAMP"
        clamp_block = "VBA_60_SCISSOR_CLAMP_PLAN"
        clamp_block_pr = "VBA_60_SCISSOR_CLAMP_PROFILE"
        clamp_block_pr_flip = "VBA_60_SCISSOR_CLAMP_PROFILE_FLIP"
    Else
        MsgBox ("Error: Column is too wide (>46"") in one dimension")
        ColumnCreator.show
        Exit Function
    End If
    
    'Determine clamp spacing
    clamp_matrix = ImportMatrix(filepath)
    
    'Find row number corresponding to longer side of column
    If x <= y Then
        long_side = y
    Else
        long_side = x
    End If
    
    For i = 0 To UBound(clamp_matrix, 1) 'Cycle through each row
        If clamp_matrix(i, 1) >= Round(long_side, 3) Then 'Look at second entry of each row and compare to the width of the long side.
            row_num = i 'If value equals or exceds that width then that's the row we want.
            Exit For
        End If
    Next i

    'Calculate the number of pours needed, given available full liquid head
    n_pours = Int(z / clamp_matrix(row_num, 0)) 'Rounds down to the nearest integer
    If Round(n_pours * clamp_matrix(row_num, 0), 3) < Round(z, 3) Then n_pours = n_pours + 1 'Adds 1 if there's any remainder
    
    'Save the original column height
    Dim z_original As Double
    z_original = z

    'Create a variable for the overlap that occurs when the remainder after a pour is < 12 inches. The next pour will be set to 12 inches and the overlap of that pour with the previous pour is pour_overlap
    Dim pour_overlap As Double: pour_overlap = 0
    
    'Define a matrix to contain all the clamp spacings for the "sub columns" if multiple pours are required. Use an arbitrary large value for the number of clamps, which is at this point unknown.
    Dim multi_clamp_spacing() As Variant
    ReDim multi_clamp_spacing(1 To 100, 1 To n_pours) '1st dimension: clamp spacing, 2nd dimension: the pour number
    Dim total_clamp_spacings() As Integer 'Tracks the size of clamp_spacing for each lift
    ReDim total_clamp_spacings(1 To n_pours)
    
    'Run through the clamp spacing procedure for each pour designing a "virtual column" for each
    For p = 1 To n_pours
        'Redefine z for the "virtual column", it must be at least 12" tall
        If n_pours >= 2 Then
            If Round(z_original - p * clamp_matrix(row_num, 0), 3) >= 0 Then
                z = clamp_matrix(row_num, 0) 'Pour goes to max allowable pour height
            Else 'Pour "tops off" column
                z = z_original - (p - 1) * clamp_matrix(row_num, 0)
                If z < 12 Then 'Ensure z is at least 12 inches, if less than 12 make it 12 and record the overlap with the previous pour
                    pour_overlap = 12 - z
                    z = 12
                End If
            End If
        End If
        
        'Build clamp spacing matrix
        ReDim clamp_spacing(1 To UBound(clamp_matrix, 2))
        k = 0

        For i = 2 To UBound(clamp_matrix, 2) 'First column (index 0) is column heights, second column (index 1) is column side dim, clamp spacings start on 3rd column (index 2)
            If clamp_matrix(row_num, i) = 0 Then 'Store all non-zero values. When a 0 is encountered, exit the loop and redim to truncate off the trailing 0s
                ReDim Preserve clamp_spacing(1 To k)
                Exit For
            Else
                clamp_spacing(i - 1) = clamp_matrix(row_num, i)
                k = k + 1
            End If
        Next i
        
        'Reduce clamp_spacing to fit actual column size. Use number of clamps for the larger size (a 9'-8" column uses clamps designed for a 10'-0" column)
        'First cut off all clamps below actual height
        Dim ht_rem As Double
        ht_rem = z - bot_clamp_gap
        n_clamps_temp = 0 'Reset number of clamps
        
        For i = 1 To UBound(clamp_spacing) - 1 'Look at the length of column above the bottom clamp
            If Round(clamp_spacing(i), 3) <= Round(ht_rem, 3) Then 'Starting at the top, subtract clamp spacings until the clamp spacing is larger than whatever distance remains
                n_clamps_temp = n_clamps_temp + 1
                ht_rem = ht_rem - clamp_spacing(i)
            Else
                n_clamps_temp = n_clamps_temp + 1 'When the clamp no longer fits add back the bottom clamp to the count and exit the loop
                Exit For
            End If
        Next i

        'Cut off all clamps below what fits onto this column and add back the bottom spacing
        ReDim Preserve clamp_spacing(1 To n_clamps_temp + 1)
        clamp_spacing(UBound(clamp_spacing)) = bot_clamp_gap

        'Sum all clamp spacings from truncated matrix
        tot_temp = 0
        For i = 1 To UBound(clamp_spacing)
            tot_temp = tot_temp + clamp_spacing(i)
        Next i
        
        'Reduce spacing of 2nd from bottom clamp so sum of clamp spacings = z
        clamp_spacing(UBound(clamp_spacing) - 1) = clamp_spacing(UBound(clamp_spacing) - 1) - (tot_temp - z)

        'Cycle through all clamp spacings and check that they're >= 5". If less, move lowest non-compliant clamp to 5" and adjust the clamp above it accordingly, repeat until all clamps pass
        Dim infExit As Integer: infExit = 0
TestClampSpacing:
        For i = 2 To UBound(clamp_spacing)
            If Round(clamp_spacing(i), 3) < 5 And i >= 2 Then
                clamp_spacing(i - 1) = clamp_spacing(i - 1) - (5 - clamp_spacing(i))
                clamp_spacing(i) = 5
                infExit = infExit + 1
                If infExit > 100 Then
                    MsgBox ("Error: Infinite loop encountered while computing clamp spacings.")
                    Exit For
                Else
                    GoTo TestClampSpacing
                End If
            End If
        Next i

        'Store the clamp spacing for this pour in multi_clamp_spacing()
        For i = 1 To UBound(clamp_spacing)
            multi_clamp_spacing(i, p) = clamp_spacing(i)
        Next i
        
        'Record total clamp spacing
        total_clamp_spacings(p) = UBound(clamp_spacing)
        
        'Record total number of clamps
        n_clamps = n_clamps + n_clamps_temp
        If p >= 2 Then n_clamps = n_clamps + 1 'On pours after the first add a clamp "between" clamp spacings
    Next p
    
    'Assemble a complete clamp spacing list from the pour(s) in multi_clamp_spacing()
    Dim clamp_spacing_r() 'Reverse order of clamp_spacings will be defined first, then flipped
    ReDim clamp_spacing_r(1 To 100)
    ReDim clamp_spacing(1 To 100)
    j = 1
    For p = n_pours To 1 Step -1
        For i = 1 To total_clamp_spacings(p)
            If multi_clamp_spacing(i, p) <> 0 Then 'Only record non-zero values, most of this array will probably be empty
                If p <> n_pours And i = 1 Then 'Combine clamp spacing between pours
                    clamp_spacing(j - 1) = multi_clamp_spacing(i, p) + multi_clamp_spacing(total_clamp_spacings(p + 1), p + 1)
                    n_clamps = n_clamps - 1
                    'MsgBox clamp_spacing(j - 1) & vbNewLine & vbNewLine & multi_clamp_spacing(i, p) & vbNewLine & multi_clamp_spacing(total_clamp_spacings(p + 1), p + 1)
                Else
                    clamp_spacing(j) = multi_clamp_spacing(i, p)
                    j = j + 1
                End If
            End If
            
        Next i
    Next p
    
    'Iif a "pour overlap" occurs, move the top-most clamp of the previus pour downward
    If pour_overlap <> 0 Then
         clamp_spacing(total_clamp_spacings(n_pours)) = clamp_spacing(total_clamp_spacings(n_pours)) + pour_overlap
         clamp_spacing(total_clamp_spacings(n_pours) + 1) = clamp_spacing(total_clamp_spacings(n_pours) + 1) - pour_overlap
    End If

    'Clean up clamp_spacing by deleting 0 values
    'Only truncate if the next 2 values are 0
    For i = 1 To UBound(clamp_spacing)
        If clamp_spacing(i) = 0 And clamp_spacing(i + 1) = 0 Then
            ReDim Preserve clamp_spacing(1 To i - 1)
            Exit For
        End If
    Next i

    msg = ""
    For i = LBound(clamp_spacing) To UBound(clamp_spacing)
        msg = msg & clamp_spacing(i) & vbNewLine
    Next i
    msg = "clamp spacing: " & vbNewLine & msg
    'MsgBox msg
    
    'Check if the top clamp is <2" from the top. If it's easy to move it to 2" by adjusting the top 3 clamp spacings, do so
    If clamp_spacing(1) < 2 And clamp_spacing(1) >= 0 Then
        If clamp_spacing(2) >= (2 - clamp_spacing(1)) + 5 Then 'Reduce 2nd-from-top clamp spacing to make room on top
            clamp_spacing(2) = clamp_spacing(2) - (2 - clamp_spacing(1))
            clamp_spacing(1) = 2
        ElseIf clamp_spacing(3) >= (2 - clamp_spacing(1)) + 5 Then 'Reduce 3rd-from-top clamp spacing to make room on top
            clamp_spacing(3) = clamp_spacing(3) - (2 - clamp_spacing(1))
            clamp_spacing(1) = 2
        End If
    End If
    
    'Restore original column height
    z = z_original
    
    'Make array of clamp locations by continuous dimensions
    Dim clamp_spacing_con()
    ReDim clamp_spacing_con(1 To UBound(clamp_spacing))
    clamp_spacing_con(1) = z - clamp_spacing(1)
    For i = 2 To UBound(clamp_spacing)
        clamp_spacing_con(i) = clamp_spacing_con(i - 1) - clamp_spacing(i)
    Next i





'#####################################################################################
'                                     T E X T
'#####################################################################################
    
    'Insert material count text
    Dim MTextObject1 As AcadMText
    Dim MTextObject2 As AcadMText
    Dim objTextStyle As AcadTextStyle
    Dim pt_click() As Double
    Dim qty_text As String
    Dim pt_o(0 To 2) As Double 'lower left corner of sheet border
    Dim pt1(0 To 2) As Double  'Fabrication notes
    Dim pt2(0 To 2) As Double  'Title text for fabrication notes and quantities
    Dim pt3(0 To 2) As Double  'Quantity/components text
    Dim panel_wt As Double  'Weight of 1 panel
    Dim BlockRefObj As AcadBlockReference 'Create block reference object used for inserting all blocks
    
    'Ask user to select point
    ThisDrawing.ActiveSpace = acModelSpace
    pt_click = ThisDrawing.Utility.GetPoint(, "Click to place")
    
    'Set origin point (lower left corner of the sheet)
    pt_o(0) = pt_click(0) + 20.23568507: pt_o(1) = pt_click(1) + 5.17943146: pt_o(2) = 0
    
    'Add border and header for text
    pt1(0) = pt_o(0) + 548.37926872: pt1(1) = pt_o(1) + 369.60966303
    Set BlockRefObj = ThisDrawing.ModelSpace.InsertBlock(pt1, "VBA_SCISSOR_CLAMP_NOTES_FRAME", 1#, 1#, 1#, 0) 'Insert plywood sheets
    
    'Call module to calculate total weight
    col_wt = wt_total(x, y, z, n_studs_x, n_studs_y, stud_type, n_clamps, clamp_size, 0)
    panel_wt = wt_panel(x, y, z, n_studs_x, n_studs_y, stud_type)
    
    'Define some other points for text
    pt1(0) = pt_o(0) + 448.4: pt1(1) = pt_o(1) + 360
    pt2(0) = pt1(0) + 0: pt2(1) = pt1(1) + 7
    pt3(0) = pt1(0) + 0: pt3(1) = pt1(1) - 68
    

    'FABRICATION NOTES AND QUANTITIES
    ThisDrawing.ActiveLayer = ThisDrawing.Layers("FORM")
    Dim strFabNotes As String
    
    strFabNotes = _
    "• COLUMN SIZE = " & x & "'' X " & y & "''" & vbCrLf & vbCrLf & _
    "• NUMBER OF COLUMN FORMS = " & n_col & "-EA" & vbCrLf & vbCrLf & _
    "• COLUMN FORM WEIGHT (APPROXIMATE) = " & col_wt & "-LBS" & vbCrLf & _
    "• COLUMN PANEL WEIGHT (SINGLE PANEL) = " & panel_wt & "-LBS" & vbCrLf & vbCrLf & _
    "• PLYWOOD = 3/4'' PLYFORM (" & ply_name & "), CLASS-1 (MIN)" & vbCrLf & vbCrLf & _
    "• COLUMN FORMS AND CLAMP SPACING LAYOUTS FOR SCISSOR CLAMPS ARE DESIGNED FOR A POUR RATE = "
    If Round(z, 3) <= Round(clamp_matrix(row_num, 0), 3) Then
        strFabNotes = strFabNotes & "FULL LIQUID HEAD U.N.O." & vbCrLf & vbCrLf
    Else
        strFabNotes = strFabNotes & ConvertFtIn(ConvertToNum(clamp_matrix(row_num, 0))) & vbCrLf & vbCrLf
    End If
    strFabNotes = strFabNotes & _
    "• CONTACT THE MCC ENGINEER PRIOR TO ANY CHANGES OR MODIFICATIONS TO THE DETAILS ON THIS SHEET."
    
    Set MTextObject1 = ThisDrawing.ModelSpace.AddMText(pt1, 100, strFabNotes)
    MTextObject1.StyleName = "Arial Narrow"
    MTextObject1.Height = 2
    
    'Plywood quantities
    For i = 1 To UBound(ply_cuts, 2)
        qty_text = qty_text & "• (" & ply_cuts(3, i) * n_col & "-EA) = (" & n_col & "-COL) X (" & ply_cuts(3, i) & "-EA/COL) @ " & ConvertFtIn(ply_cuts(1, i)) & " WIDE X " & ConvertFtIn(ply_cuts(2, i)) & " LONG 3/4'' PLYWOOD" & vbCrLf
    Next i
    qty_text = "PLYWOOD" & vbCrLf & qty_text & vbCrLf
    
    'Stud quantities
    qty_text = qty_text & "STUDS" & vbCrLf & "• (" & n_studs_total * n_col & "-EA) = (" & n_col & "-COL) X (" & n_studs_total & "-EA/COL) @ " & ConvertFtIn(z - 0.25) & " " & stud_name_full
    
    'Clamp quantities
    qty_text = qty_text & vbCrLf & vbCrLf & "SCISSOR CLAMP SETS (2 CLAMPS PER SET)" & vbCrLf
    qty_text = qty_text & "• (" & n_clamps * n_col & "-EA) = (" & n_col & "-COL) X (" & n_clamps & "-EA/COL) @ " & clamp_name & " SETS"
    
    'Chamfer quantity
    'qty_text = qty_text & "3/4'' GATES PLASTIC CHAMFER (BASED ON 12' CHAMFER LENGTHS)" & vbCrLf & _
    '"•   (" & n_col * n_chamf & "-EA) = (" & n_col & "-COL) X (" & n_chamf & "-EA/COL) @ " & chamf_length & "'-0'' LONG PIECES"
    
    'Set all count and fab note texts
    Set MTextObject1 = ThisDrawing.ModelSpace.AddMText(pt3, 100, qty_text)
    MTextObject1.Height = 2
    MTextObject1.StyleName = "Arial Narrow" 'Forces use of Arial Narrow text style
        
        
        
        

    '#####################################################################################
    '                                 D R A W I N G
    '#####################################################################################

    Dim ObjDynBlockProp As AcadDynamicBlockReferenceProperty
    Dim LineObj As AcadLine
    Dim PlyTemp As Double
    Dim ptA(0 To 2) As Double 'lower left corner of side A elevation view plywood
    Dim ptB(0 To 2) As Double 'lower left corner of side B elevation view plywood
    Dim ptE(0 To 2) As Double 'Lower left corner of clamp elevation view (right side of ply edge)
    
    Dim pt4(0 To 2) As Double 'Plywood seam locations for sides A and B
    Dim pt5(0 To 2) As Double 'Stud locations on turned out clamp in plan view
    Dim pt6(0 To 2) As Double 'stud locations for sides A, B, and W
    Dim pt7(0 To 2) As Double 'UNUSED
    Dim pt8(0 To 2) As Double 'Elevation section ply base for side A
    Dim pt9(0 To 2) As Double 'Elevation section ply base for side B
    Dim pt10(0 To 2) As Double 'Elevation section ply base for side W
    Dim pt11(0 To 2) As Double 'stud locations at elevation section for sides A, B, and W
    Dim pt12(0 To 2) As Double 'ply+chamfer for plan view
    Dim pt13(0 To 2) As Double 'origin point on plan view
    Dim pt14(0 To 2) As Double 'stud locs for plan view
    Dim pt15(0 To 2) As Double 'clamp locs for plan view
    Dim pt16(0 To 2) As Double 'brace locs for plan view
    Dim pt17(0 To 2) As Double 'Text locs for plan view
    Dim pt18(0 To 2) As Double 'Chamfer locations for elevation views
    Dim pt19(0 To 2) As Double
    Dim pt20(0 To 2) As Double 'stud locations at base of clamp elevation and framing lumber at base
    Dim pt21(0 To 2) As Double 'Clamp locations in elevation
    Dim pt22(0 To 2) As Double 'Clamp dimensions in inches from bottom
    Dim pt23(0 To 2) As Double 'Start point for top clamp dim line
    Dim pt24(0 To 2) As Double 'End point for top clamp dim line
    Dim pt25(0 To 2) As Double '"CLAMP" and "TOP CLAMP" labels
    Dim pt26(0 To 2) As Double 'Lifting sling points
    Dim pt27(0 To 2) As Double 'Coil rod and nuts for top clamps
    Dim pt28(0 To 2) As Double 'Brace related locations
    Dim pt29(0 To 2) As Double 'Screw heads for ply elevations
    Dim pt30(0 To 2) As Double 'Misc. notes and details
    Dim pt31(0 To 2) As Double 'Reinforcing angles for wide columns
    Dim pt32(0 To 2) As Double 'Lower left text for column count
    Dim pt33(0 To 2) As Double 'A & B elevation sights for plan views
    Dim pt34(0 To 2) As Double 'Insertion point for timestamp (lower left corner, outside of sheet)
    Dim pt_blk(0 To 2) As Double
    
    'Control which elevation views are drawn and space them accordingly
    Dim DrawB As Boolean: DrawB = True    'Side B (if different)

    'Define reference points for each view
    ptA(0) = pt_o(0) + 300: ptA(1) = pt_o(1) + 25
    ptB(0) = pt_o(0) + 185: ptB(1) = pt_o(1) + 25
    ptE(0) = pt_o(0) + 54.5: ptE(1) = pt_o(1) + 25
    DrawB = True

    'ELEVATION VIEWS
    ThisDrawing.ActiveLayer = ThisDrawing.Layers("FORM")
    
    'Profile of other side's studs (left)
    Call DrawRectangle(ptE(0) - ply_thk, ptE(1) + stud_base_gap, ptE(0) - ply_thk - 1.5, ptE(1) + z)
    
    'Profile of other side's studs (right)
    Call DrawRectangle(ptE(0) + ply_width_e + ply_thk, ptE(1) + stud_base_gap, ptE(0) + ply_width_e + ply_thk + 1.5, ptE(1) + z)
    
    'Draw studs
        'Side A
        For i = 1 To n_studs_x
            pt6(0) = ptA(0) + ply_width_x - 3.5 - stud_spacing_x(i)
            pt6(1) = ptA(1) + stud_base_gap
            Set BlockRefObj = ThisDrawing.ModelSpace.InsertBlock(pt6, stud_face_block, 1#, 1#, 1#, pi / 2) 'Insert studs
            Call ChangeProp(BlockRefObj, "Distance1", z - stud_base_gap)
        Next i
        
        'Side B
        For i = 1 To n_studs_y
            pt6(0) = ptB(0) + ply_width_y - 3.5 - stud_spacing_y(i)
            pt6(1) = ptB(1) + stud_base_gap
            Set BlockRefObj = ThisDrawing.ModelSpace.InsertBlock(pt6, stud_face_block, 1#, 1#, 1#, pi / 2) 'Insert studs
            Call ChangeProp(BlockRefObj, "Distance1", z - stud_base_gap)
        Next i
        
    'Draw plywood sheets
    ThisDrawing.ActiveLayer = ThisDrawing.Layers("PLYA")
    pt4(1) = ptA(1)
    For i = 1 To UBound(ply_seams)
        pt4(0) = ptA(0)
        pt4(1) = pt4(1) + ply_seams(i)
        Set BlockRefObj = ThisDrawing.ModelSpace.InsertBlock(pt4, "VBA_PLY_SHEET", 1#, 1#, 1#, 0) 'Insert plywood sheets
        Call ChangeProp(BlockRefObj, "Distance1", ply_width_x)
        Call ChangeProp(BlockRefObj, "Distance2", ply_seams(i))
    
        pt4(0) = ptB(0)
        Set BlockRefObj = ThisDrawing.ModelSpace.InsertBlock(pt4, "VBA_PLY_SHEET", 1#, 1#, 1#, 0) 'Insert plywood sheets
        Call ChangeProp(BlockRefObj, "Distance1", ply_width_y)
        Call ChangeProp(BlockRefObj, "Distance2", ply_seams(i))
    Next i


    'Draw elevation view (clamps view) specifc items
    'Studs
    ThisDrawing.ActiveLayer = ThisDrawing.Layers("FORM")
    For i = 1 To n_studs_e
        pt20(0) = ptE(0) + stud_spacing_e(i): pt20(1) = ptE(1) + stud_base_gap
        Set BlockRefObj = ThisDrawing.ModelSpace.InsertBlock(pt20, stud_face_block, 1#, 1#, 1#, pi / 2) 'Insert studs
        Call ChangeProp(BlockRefObj, "Distance1", z - stud_base_gap): Call ChangeProp(BlockRefObj, "Visibility1", "Solid")
    Next i
    
    'Plywood
    'Outer ply boundry of elevation view
    ThisDrawing.ActiveLayer = ThisDrawing.Layers("PLYA")
    Call DrawRectangle(ptE(0), ptE(1), ptE(0) + ply_width_e, ptE(1) + z)
    
    'Plywood edge view
    pt21(0) = ptE(0): pt21(1) = ptE(1)
    Set BlockRefObj = ThisDrawing.ModelSpace.InsertBlock(pt21, "VBA_PLY", 1#, 1#, 1#, pi / 2) 'left ply
    Call ChangeProp(BlockRefObj, "Distance1", z)
    pt21(0) = ptE(0) + ply_width_e + ply_thk: pt21(1) = ptE(1)
    Set BlockRefObj = ThisDrawing.ModelSpace.InsertBlock(pt21, "VBA_PLY", 1#, 1#, 1#, pi / 2) 'right ply
    Call ChangeProp(BlockRefObj, "Distance1", z)
    
    'Clamps and dims
    'Add top clamp dim
    ThisDrawing.ActiveLayer = ThisDrawing.Layers("FMTEXTA")
    pt21(0) = ptE(0) - 2.25: pt21(1) = ptE(1) + z
    Call DrawDimLin(pt21(0) + x + 4.5 + clamp_width, pt21(1) - clamp_spacing(1), pt21(0) + ply_width_e + 3.75 + ply_thk, pt21(1), pt21(0) + clamp_L + 5, (pt21(1) * 2 - clamp_spacing(1)) / 2, pi / 2)
    
    For i = 1 To n_clamps
        'Draw clamps and dims
        pt21(1) = pt21(1) - clamp_spacing(i)
        If i Mod 2 = 0 Then
            pt19(0) = pt21(0): pt19(1) = pt21(1)
            Set BlockRefObj = ThisDrawing.ModelSpace.InsertBlock(pt19, clamp_block_pr, 1#, 1#, 1#, 0) 'Draw clamp profile view
        Else
            pt19(0) = pt21(0) + 4.5 + x: pt19(1) = pt21(1)
            Set BlockRefObj = ThisDrawing.ModelSpace.InsertBlock(pt19, clamp_block_pr_flip, 1#, 1#, 1#, 0) 'Draw clamp profile view
        End If
        Call ChangeProp(BlockRefObj, "Distance1", 4.5 + ply_width_e)
        
        'Draw dimensions between clamps
        If i <> 1 Then
            If i Mod 2 = 0 Then
                Call DrawDimLin(pt21(0) + clamp_L, pt21(1), pt21(0) + x + 4.5 + clamp_width, pt21(1) + clamp_spacing(i), pt21(0) + clamp_L + 5, (pt21(1) * 2 + clamp_spacing(i)) / 2, -pi / 2)
            Else
                Call DrawDimLin(pt21(0) + x + 4.5 + clamp_width, pt21(1), pt21(0) + clamp_L, pt21(1) + clamp_spacing(i), pt21(0) + clamp_L + 5, (pt21(1) * 2 + clamp_spacing(i)) / 2, -pi / 2)
            End If
        End If

        'Draw inches from bottom
        pt22(0) = pt21(0) + clamp_L + 7: pt22(1) = ptE(1) + clamp_spacing_con(i) + 1.25   'pt21(0) - clamp_width - 8
        clamp_str = CStr(clamp_spacing_con(i)) & """" 'ConvertFtIn(clamp_spacing_con(i))
        Set MTextObject2 = ThisDrawing.ModelSpace.AddMText(pt22, 10, clamp_str)
        MTextObject2.Height = 2.5
    Next i
    
    'Add bottom clamp dim
    If i Mod 2 = 0 Then
        Call DrawDimLin(pt21(0) + x + 4.5 + clamp_width, ptE(1) + bot_clamp_gap, pt21(0) + ply_width_e + 2.25 + ply_thk + 2.75, ptE(1), pt21(0) + clamp_L + 5, (2 * ptE(1) + bot_clamp_gap) / 2, pi / 2)
    Else
        Call DrawDimLin(pt21(0) + clamp_L, ptE(1) + bot_clamp_gap, pt21(0) + ply_width_e + 2.25 + ply_thk + 2.75, ptE(1), pt21(0) + clamp_L + 5, (2 * ptE(1) + bot_clamp_gap) / 2, pi / 2)
    End If
    
    'Mark allowable pour heights
    Dim strOrdinal As String
    If n_pours >= 2 Then
        ThisDrawing.ActiveLayer = ThisDrawing.Layers("NOTES")
        For i = 1 To n_pours - 1
            'Draw a dotted line at that height
            pt20(0) = ptE(0) - 24: pt20(1) = ptE(1) + clamp_matrix(row_num, 0) * i
            pt21(0) = ptE(0) + x + 58: pt21(1) = ptE(1) + clamp_matrix(row_num, 0) * i
            Set LineObj = ThisDrawing.ModelSpace.AddLine(pt20, pt21)
            LineObj.Linetype = "HIDDEN"
            'color.ColorIndex = acYellow
            'LineObj.TrueColor = color
            
            'Add text
            'Determine which to use for the ordinal count: st, nd, rd, or th
            ThisDrawing.ActiveLayer = ThisDrawing.Layers("FMTEXTA")
            If i >= 11 And i <= 19 Then
                strOrdinal = "TH"
            ElseIf Right(i, 1) = 1 Then
                strOrdinal = "ST"
            ElseIf Right(i, 1) = 2 Then
                strOrdinal = "ND"
            ElseIf Right(i, 1) = 3 Then
                strOrdinal = "RD"
            Else
                strOrdinal = "TH"
            End If
            pt20(0) = ptE(0) + x + 40: pt20(1) = ptE(1) + clamp_matrix(row_num, 0) * i + 3.25
            Set mtextobj = ThisDrawing.ModelSpace.AddMText(pt20, 24, "MAX HT OF " & vbNewLine & i & strOrdinal & " POUR")
            mtextobj.Height = 2.5
            
            'Add height
            pt20(0) = ptE(0) - 32: pt20(1) = ptE(1) + clamp_matrix(row_num, 0) * i + 1.25
            Set mtextobj = ThisDrawing.ModelSpace.AddMText(pt20, 8, i * clamp_matrix(row_num, 0) & """")
            mtextobj.Height = 2.5
        Next i
    End If
    
    'Base framing lumber
    ThisDrawing.ActiveLayer = ThisDrawing.Layers("FORM")
    pt20(0) = ptE(0) - ply_thk - 1.5 - 3.5: pt20(1) = ptE(1)
    Set BlockRefObj = ThisDrawing.ModelSpace.InsertBlock(pt20, "VBA_2X4", 1#, 1#, 1#, 0) 'Insert studs
    pt20(0) = ptE(0) + ply_width_e: pt20(1) = ptE(1)
    Set BlockRefObj = ThisDrawing.ModelSpace.InsertBlock(pt20, "VBA_2X4", 1#, 1#, 1#, 0) 'Insert studs
    pt20(0) = ptE(0) - ply_thk - 1.5 - 6: pt20(1) = ptE(1) + 3
    Set BlockRefObj = ThisDrawing.ModelSpace.InsertBlock(pt20, "VBA_2X4_SIDE", 1#, 1#, 1#, 0) 'Insert studs
    Call ChangeProp(BlockRefObj, "Distance1", ply_width_e + ply_thk + 1.5 + 12)
    pt30(0) = ptE(0) + ply_width_e + 6: pt30(1) = ptE(1) + 2.25
    Set BlockRefObj = ThisDrawing.ModelSpace.InsertBlock(pt30, "VBA_DOWN_PLATE_NOTES_SCISSOR", 1#, 1#, 1#, 0)


    'Draw panel sections
    'Side A
    pt8(0) = ptA(0) + ply_width_x: pt8(1) = ptA(1) + z + 18
    Set BlockRefObj = ThisDrawing.ModelSpace.InsertBlock(pt8, "VBA_PLY", 1#, 1#, 1#, pi) 'Insert ply
    Call ChangeProp(BlockRefObj, "Distance1", ply_width_x)
    For i = 1 To n_studs_x
        pt11(0) = ptA(0) + ply_width_x - 3.5 - stud_spacing_x(i)
        pt11(1) = ptA(1) + z + 18
        Set BlockRefObj = ThisDrawing.ModelSpace.InsertBlock(pt11, stud_block, 1#, 1#, 1#, 0) 'Insert studs
    Next i
    
    'Side B
    pt9(0) = ptB(0) + ply_width_y: pt9(1) = ptB(1) + z + 18
    Set BlockRefObj = ThisDrawing.ModelSpace.InsertBlock(pt9, "VBA_PLY", 1#, 1#, 1#, pi) 'Insert ply
    Call ChangeProp(BlockRefObj, "Distance1", ply_width_y)
    For i = 1 To n_studs_y
        pt11(0) = ptB(0) + ply_width_y - 3.5 - stud_spacing_y(i)
        pt11(1) = ptB(1) + z + 18
        Set BlockRefObj = ThisDrawing.ModelSpace.InsertBlock(pt11, stud_block, 1#, 1#, 1#, 0) 'Insert studs
    Next i

    'Dim sections
        'Side A
        Call DrawDim(pt8(0), pt8(1) - ply_thk, pt8(0) - ply_width_x, pt8(1) - ply_thk, (pt8(0) - ply_width_x - pt8(0)) / 2, pt8(1) - ply_thk - 5) 'Dimension plywood
        For i = 1 To n_studs_x
            Call DrawDimLin(pt8(0) - stud_spacing_x(UBound(stud_spacing_x) - i + 1), pt8(1) + 1.5, pt8(0) - ply_width_x, pt8(1), ((pt8(0) - ply_width_x) - (pt8(0) - stud_spacing_x(UBound(stud_spacing_x) - i + 1))) / 2, pt8(1) + 4 + i * 4, 0)   'Dimension studs from rightmost (in plan) stud
        Next i
        Call DrawDimLin(pt8(0) - stud_spacing_x(UBound(stud_spacing_x)) - 3.5, pt8(1) + 1.5, pt8(0) - ply_width_x, pt8(1), ((pt8(0) - ply_width_x) - (pt8(0) - stud_spacing_x(UBound(stud_spacing_x)) - 3.5)) / 2, pt8(1) + 4, 0)   'Dimension leftmost (in plan) stud to face of ply
        Call DrawDimLin(pt8(0) - stud_start_offset_x, pt8(1) + 1.5, pt8(0), pt8(1), ((pt8(0)) - (pt8(0) - stud_start_offset_x)) / 2, pt8(1) + 4 * (n_studs_x + 1), 0)    'dimension stud_start_gap
        
        'Side B
        Call DrawDim(pt9(0), pt9(1) - ply_thk, pt9(0) - ply_width_y, pt9(1) - ply_thk, (pt9(0) - ply_width_y - pt9(0)) / 2, pt9(1) - ply_thk - 5) 'Dimension plywood
        For i = 1 To n_studs_y
            Call DrawDimLin(pt9(0) - stud_spacing_y(UBound(stud_spacing_y) - i + 1), pt9(1) + 1.5, pt9(0) - ply_width_y, pt9(1), ((pt9(0) - ply_width_y) - (pt9(0) - stud_spacing_y(UBound(stud_spacing_y) - i + 1))) / 2, pt9(1) + 4 + i * 4, 0)   'Dimension studs from rightmost (in plan) stud
        Next i
        Call DrawDimLin(pt9(0) - stud_spacing_y(UBound(stud_spacing_y)) - 3.5, pt9(1) + 1.5, pt9(0) - ply_width_y, pt9(1), ((pt9(0) - ply_width_y) - (pt9(0) - stud_spacing_y(UBound(stud_spacing_y)) - 3.5)) / 2, pt9(1) + 4, 0)   'Dimension leftmost (in plan) stud to face of ply
        Call DrawDimLin(pt9(0) - stud_start_offset_y, pt9(1) + 1.5, pt9(0), pt9(1), ((pt9(0)) - (pt9(0) - stud_start_offset_y)) / 2, pt9(1) + 4 * (n_studs_y + 1), 0)    'dimension stud_start_gap

        'Set BlockRefObj = ThisDrawing.ModelSpace.InsertBlock(pt9, "VBA_TOP_SECTION_DETAILS1", 1#, 1#, 1#, 0) 'Insert text notes, blow up detail at top section
    
    'Dim plywood
        'Side A
        PlyTemp = ptA(1) + ply_seams(1)
        Call DrawDimSuffix(ptA(0) + ply_width_x, ptA(1), ptA(0) + ply_width_x, PlyTemp, ptA(0) + ply_width_x + 6, (PlyTemp - ptA(1)) / 2, " PLYWOOD")
        If UBound(ply_seams) >= 2 Then 'If more than one ply panel, draw the rest, bottom up
            For i = 2 To UBound(ply_seams)
                PlyTemp = PlyTemp + ply_seams(i)
                Call DrawDimSuffix(ptA(0) + ply_width_x, PlyTemp - ply_seams(i), ptA(0) + ply_width_x, PlyTemp, ptA(0) + ply_width_x + 6, (PlyTemp - (PlyTemp - ply_seams(i))) / 2, " PLYWOOD")
            Next i
        End If
        Call DrawDimSuffix(ptA(0), ptA(1), ptA(0), ptA(1) + z, ptA(0) - 9, (2 * ptA(1) + z) / 2, " OVERALL HEIGHT")
        Call DrawDimSuffix(ptA(0), ptA(1) + stud_base_gap, ptA(0), ptA(1) + z, ptA(0) - 4.5, ((ptA(1) + z) + (ptA(1) + stud_base_gap)) / 2, " STUD")
        Call DrawDimSuffix(ptA(0) + ply_width_x, ptA(1) + z, ptA(0), ptA(1) + z, (2 * ptA(0) + ply_width_x) / 2, ptA(1) + z + 4, " PLYWOOD")
        
        'Side B
        PlyTemp = ptB(1) + ply_seams(1)
        Call DrawDimSuffix(ptB(0) + ply_width_y, ptB(1), ptB(0) + ply_width_y, PlyTemp, ptB(0) + ply_width_y + 6, (PlyTemp - ptB(1)) / 2, " PLYWOOD")
        If UBound(ply_seams) >= 2 Then 'If more than one ply panel, draw the rest, bottom up
            For i = 2 To UBound(ply_seams)
                PlyTemp = PlyTemp + ply_seams(i)
                Call DrawDimSuffix(ptB(0) + ply_width_y, PlyTemp - ply_seams(i), ptB(0) + ply_width_y, PlyTemp, ptB(0) + ply_width_y + 6, (PlyTemp - (PlyTemp - ply_seams(i))) / 2, " PLYWOOD")
            Next i
        End If
        Call DrawDimSuffix(ptB(0), ptB(1), ptB(0), ptB(1) + z, ptB(0) - 9, (2 * ptB(1) + z) / 2, " OVERALL HEIGHT")
        Call DrawDimSuffix(ptB(0), ptB(1) + stud_base_gap, ptB(0), ptB(1) + z, ptB(0) - 4.5, ((ptB(1) + z) + (ptB(1) + stud_base_gap)) / 2, " STUD")
        Call DrawDimSuffix(ptB(0) + ply_width_y, ptB(1) + z, ptB(0), ptB(1) + z, (2 * ptB(0) + ply_width_y) / 2, ptB(1) + z + 4, " PLYWOOD")



            
    'PLAN VIEWS
    pt13(0) = pt_o(0) + 427 + x - chamf_thk: pt13(1) = pt_o(1) + 42 + ply_thk 'origin point for plan views (lower right corner)

    'Draw clamps
    pt15(0) = pt13(0) - x - 2.25: pt15(1) = pt13(1) - 2.25
    Set BlockRefObj = ThisDrawing.ModelSpace.InsertBlock(pt15, clamp_block, 1#, 1#, 1#, 0) 'Insert clamp (operator typical clamps)
    Call ChangeProp(BlockRefObj, "Distance1", x + 4.5)
    Call ChangeProp(BlockRefObj, "Distance2", y + 4.5)
    
    'Draw plywood
    pt12(0) = pt13(0) - x: pt12(1) = pt13(1) - ply_thk
    Set BlockRefObj = ThisDrawing.ModelSpace.InsertBlock(pt12, "VBA_PLY", 1#, 1#, 1#, 0) 'Bottom ply
    Call ChangeProp(BlockRefObj, "Distance1", ply_width_x)
    
    pt12(0) = pt12(0) - ply_thk: pt12(1) = pt12(1) + ply_width_y + ply_thk - 2.25
    Set BlockRefObj = ThisDrawing.ModelSpace.InsertBlock(pt12, "VBA_PLY", 1#, 1#, 1#, -pi / 2) 'Left ply
    Call ChangeProp(BlockRefObj, "Distance1", ply_width_y)
    
    pt12(0) = pt12(0) + ply_thk + ply_width_x: pt12(1) = pt12(1) + ply_thk - 2.25
    Set BlockRefObj = ThisDrawing.ModelSpace.InsertBlock(pt12, "VBA_PLY", 1#, 1#, 1#, pi) 'Top ply
    Call ChangeProp(BlockRefObj, "Distance1", ply_width_x)
    
    pt12(0) = pt12(0) + ply_thk: pt12(1) = pt12(1) - ply_thk - ply_width_y + 2.25
    Set BlockRefObj = ThisDrawing.ModelSpace.InsertBlock(pt12, "VBA_PLY", 1#, 1#, 1#, pi / 2) 'Right ply
    Call ChangeProp(BlockRefObj, "Distance1", ply_width_y)


    'Draw studs
    pt14(1) = pt13(1) - ply_thk - 1.5
    For i = 1 To n_studs_x
        pt14(0) = pt13(0) - x + stud_spacing_x(i)
        Set BlockRefObj = ThisDrawing.ModelSpace.InsertBlock(pt14, stud_block, 1#, 1#, 1#, 0) 'Insert bottom studs
    Next i
    pt14(0) = pt13(0) - x + stud_spacing_x(UBound(stud_spacing_x))

    pt14(0) = pt13(0) - x - ply_thk - 1.5
    For i = 1 To n_studs_y
        pt14(1) = pt13(1) + y + 2.25 - stud_spacing_y(i)
        Set BlockRefObj = ThisDrawing.ModelSpace.InsertBlock(pt14, stud_block, 1#, 1#, 1#, -pi / 2) 'Insert left studs
    Next i
    
    pt14(1) = pt13(1) + y + ply_thk + 1.5
    For i = 1 To n_studs_x
        pt14(0) = pt13(0) - stud_spacing_x(i)
        Set BlockRefObj = ThisDrawing.ModelSpace.InsertBlock(pt14, stud_block, 1#, 1#, 1#, pi) 'Insert top studs
    Next i
    
    pt14(0) = pt13(0) + ply_thk + 1.5
    For i = 1 To n_studs_y
        pt14(1) = pt13(1) - 2.25 + stud_spacing_y(i)
        Set BlockRefObj = ThisDrawing.ModelSpace.InsertBlock(pt14, stud_block, 1#, 1#, 1#, pi / 2) 'Insert right studs
    Next i

    'Draw elevation tag
    pt14(0) = pt13(0) - x / 2: pt14(1) = pt13(1) - 12
    Set BlockRefObj = ThisDrawing.ModelSpace.InsertBlock(pt14, "VBA_ELEV_A", 1#, 1#, 1#, 0)
    
    'Draw hatch
    ThisDrawing.ActiveLayer = ThisDrawing.Layers("CONC")
    Dim hatchObj As AcadHatch
    Dim OuterLoop(0) As AcadEntity
    Dim pl_pts(0 To 9) As Double
    
    'Set boundry of hatch (must close hatch by returning to initial point)
    pl_pts(0) = pt13(0):     pl_pts(1) = pt13(1)
    pl_pts(2) = pt13(0) - x: pl_pts(3) = pt13(1)
    pl_pts(4) = pt13(0) - x: pl_pts(5) = pt13(1) + y
    pl_pts(6) = pt13(0):     pl_pts(7) = pt13(1) + y
    pl_pts(8) = pt13(0):     pl_pts(9) = pt13(1)
    
    Set OuterLoop(0) = ThisDrawing.ModelSpace.AddLightWeightPolyline(pl_pts) 'Assign the pline object as the hatch's outer loop (inner loop optional and skipped here)
    Set hatchObj = ThisDrawing.ModelSpace.AddHatch(0, "AR-CONC", True) 'Set hatch
    hatchObj.AppendOuterLoop (OuterLoop)
    OuterLoop(0).Delete
    
    'Draw chamfer in each corner
    pt14(0) = pt13(0): pt14(1) = pt13(1)
    Set BlockRefObj = ThisDrawing.ModelSpace.InsertBlock(pt14, "VBA_3-4_CHAMFER", 1#, 1#, 1#, 0) 'Lower right

    pt14(0) = pt13(0) - x: pt14(1) = pt13(1)
    Set BlockRefObj = ThisDrawing.ModelSpace.InsertBlock(pt14, "VBA_3-4_CHAMFER", 1#, 1#, 1#, -pi / 2) 'Lower left
    
    pt14(0) = pt13(0) - x: pt14(1) = pt13(1) + y
    Set BlockRefObj = ThisDrawing.ModelSpace.InsertBlock(pt14, "VBA_3-4_CHAMFER", 1#, 1#, 1#, pi) 'Upper left
    
    pt14(0) = pt13(0): pt14(1) = pt13(1) + y
    Set BlockRefObj = ThisDrawing.ModelSpace.InsertBlock(pt14, "VBA_3-4_CHAMFER", 1#, 1#, 1#, pi / 2) 'Upper right
    
    
    'Draw text in plan view
    ThisDrawing.ActiveLayer = ThisDrawing.Layers("FORM")
    pt17(0) = pt13(0) - x: pt17(1) = pt13(1) + y - 0.5
    Set MTextObject1 = ThisDrawing.ModelSpace.AddMText(pt17, x, "SIDE A")
    MTextObject1.StyleName = "Arial Narrow": MTextObject1.AttachmentPoint = acAttachmentPointTopCenter: MTextObject1.Height = 1.75 * Abs(Round(x, 3) >= 12) + (1.75 - 0.125 * (12 - x)) * Abs(Round(x, 3) < 12) 'Uses a text size of 1.75 when the x side of the column is >= 12", text size is reduced by 0.125" for every 1" the x side is below 12"

    pt17(0) = pt13(0) - x + 0.5: pt17(1) = pt13(1)
    Set MTextObject1 = ThisDrawing.ModelSpace.AddMText(pt17, y, "SIDE B")
    MTextObject1.StyleName = "Arial Narrow": MTextObject1.Rotation = pi / 2: MTextObject1.AttachmentPoint = acAttachmentPointTopCenter: MTextObject1.Height = 1.75 * Abs(Round(y, 3) >= 12) + (1.75 - 0.125 * (12 - y)) * Abs(Round(y, 3) < 12) 'Uses a text size of 1.75 when the y side of the column is >= 12", text size is reduced by 0.125" for every 1" the y side is below 12"
    
    pt17(0) = pt13(0) - x: pt17(1) = pt13(1) + 2.25
    Set MTextObject1 = ThisDrawing.ModelSpace.AddMText(pt17, x, x)
    MTextObject1.StyleName = "Arial Narrow": MTextObject1.AttachmentPoint = acAttachmentPointTopCenter: MTextObject1.Height = 1.75 * Abs(Round(x, 3) >= 12) + (1.75 - 0.125 * (12 - x)) * Abs(Round(x, 3) < 12) 'Uses a text size of 1.75 when the x side of the column is >= 12", text size is reduced by 0.125" for every 1" the x side is below 12"
    
    pt17(0) = pt13(0) - 2.25: pt17(1) = pt13(1)
    Set MTextObject1 = ThisDrawing.ModelSpace.AddMText(pt17, y, y)
    MTextObject1.StyleName = "Arial Narrow": MTextObject1.Rotation = pi / 2: MTextObject1.AttachmentPoint = acAttachmentPointTopCenter: MTextObject1.Height = 1.75 * Abs(Round(y, 3) >= 12) + (1.75 - 0.125 * (12 - y)) * Abs(Round(y, 3) < 12) 'Uses a text size of 1.75 when the y side of the column is >= 12", text size is reduced by 0.125" for every 1" the y side is below 12"


    'Add stud holdback detail and callout
    'Detail on top of sheet
    pt_blk(0) = ptB(0) + (x + 4.5) / 2 - 14: pt_blk(1) = pt_o(1) + 315
    Set BlockRefObj = ThisDrawing.ModelSpace.InsertBlock(pt_blk, "VBA_STUD_HOLDBACK_DETAIL", 1, 1, 1, 0)
    
    'Callout on panel
    pt_blk(0) = ptB(0) + x + 4.5: pt_blk(1) = ptB(1)
    Set BlockRefObj = ThisDrawing.ModelSpace.InsertBlock(pt_blk, "VBA_STUD_HOLDBACK_CALLOUT", 1, 1, 1, 0)
    
    'Add nailing note
    pt_blk(0) = ptB(0) + x + 0.375: pt_blk(1) = ptB(1) + 0.95 * ply_seams(1)
    Set BlockRefObj = ThisDrawing.ModelSpace.InsertBlock(pt_blk, "VBA_NAILING_NOTES_SCISSOR", 1, 1, 1, 0)
    
    'Add detail references to each elevation view
    'Plan view detail reference
    pt_blk(0) = pt13(0) - ply_width_x / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "D"
        End If
        If AttList(i).TextString = "DESCRIPTION" Then
            AttList(i).TextString = "PLAN VIEW"
        End If
        If AttList(i).TextString = "REFERENCE" Then
            AttList(i).TextString = ""
        End If
    Next i
    
    'Side A detail reference
    pt_blk(0) = ptA(0) + ply_width_x / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "C"
        End If
        If AttList(i).TextString = "DESCRIPTION" Then
            AttList(i).TextString = "SIDE ""A"" PANEL"
        End If
        If AttList(i).TextString = "REFERENCE" Then
            AttList(i).TextString = "VIEWED FROM PLYWOOD FACE"
        End If
    Next i
    
    'Side B detail reference
    pt_blk(0) = ptB(0) + ply_width_y / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "B"
        End If
        If AttList(i).TextString = "DESCRIPTION" Then
            AttList(i).TextString = "SIDE ""B"" PANEL"
        End If
        If AttList(i).TextString = "REFERENCE" Then
            AttList(i).TextString = "VIEWED FROM PLYWOOD FACE"
        End If
    Next i
        
    'Elevation view detail reference
    pt_blk(0) = ptE(0) + ply_width_e / 2: pt_blk(1) = pt_o(1) + 9
    Set BlockRefObj = ThisDrawing.ModelSpace.InsertBlock(pt_blk, "VBA_DETAIL_REF", 0.75, 0.75, 0.75, 0)
    AttList = BlockRefObj.GetAttributes
    For i = LBound(AttList) To UBound(AttList) 'Assign attribute values
        If AttList(i).TextString = "X" Then
            AttList(i).TextString = "A"
        End If
        If AttList(i).TextString = "DESCRIPTION" Then
            AttList(i).TextString = "COLUMN FORM ELEVATION"
        End If
        If AttList(i).TextString = "REFERENCE" Then
            AttList(i).TextString = ""
        End If
    Next i
    
    'Add lower left fab count below "column form elevation"
    ThisDrawing.ActiveLayer = ThisDrawing.Layers("FORM")
    count_str = "FAB " & n_col & "-EA"
    pt32(0) = ptE(0) + ply_width_e / 2: pt32(1) = pt_o(1) + 7
    Set MTextObject2 = ThisDrawing.ModelSpace.AddMText(pt32, 30, count_str)
    MTextObject2.Height = 2.5


    
'#####################################################################################
'                                S H E E T I N G
'#####################################################################################
   
    Dim ptVP1(0 To 2) As Double
    Dim ptVP2(0 To 2) As Double
    Dim pt35(0 To 2) As Double
    Dim AreaName As String
    Dim oprop As AcadDynamicBlockReferenceProperty
    
    'Insert the McClone area block
    AreaName = CStr(ColumnCreator.sAreaBox.Value)
    pt35(0) = pt_o(0) + 548.37926872: pt35(1) = pt_o(1) + 186: pt35(2) = 0
    Set BlockRefObj = ThisDrawing.ModelSpace.InsertBlock(pt35, "VBA_OFFICE_LOCATION", (2 / 3), (2 / 3), (2 / 3), 0)
    
    Props = BlockRefObj.GetDynamicBlockProperties
    For i = LBound(Props) To UBound(Props)
        Set oprop = Props(i) 'Get object properties from border block
        If oprop.PropertyName = "Visibility1" Then 'Finds visibility state property
            oprop.Value = ColumnCreator.sAreaBox.Value
        End If
    Next i
    
    'Insert border
    Set BlockRefObj = ThisDrawing.ModelSpace.InsertBlock(pt_click, "VBA_24X36_LAYOUT", 1#, 1#, 1#, 0) 'Insert 3/4" = 1'-0" sheet boundry
    BlockRefObj.ScaleEntity pt_click, 12 / 0.75
    
    'Sets Sheet issued for: "" text (defined as a block reference property)
    Props = BlockRefObj.GetDynamicBlockProperties
    For i = LBound(Props) To UBound(Props)
        Set oprop = Props(i) 'Get object properties from border block
        If oprop.PropertyName = "Visibility1" Then 'Finds visibility state property
            oprop.Value = ColumnCreator.sSheetIssuedForBox.Value
        End If
    Next i
    
    'Place timestamp in lower left corner, outside of sheet boundry
    pt34(0) = pt_o(0) - 1.65: pt34(1) = pt_o(1): pt34(2) = pt_o(2)
    ThisDrawing.ActiveTextStyle = ThisDrawing.TextStyles("VBA_txt_narrow")
    Set MTextObject2 = ThisDrawing.ModelSpace.AddMText(pt34, 18, Now())
    MTextObject2.Height = 1.25
    MTextObject2.Rotate pt34, pi / 2
    
    'Places other text (defined as attributes)
    AttList = BlockRefObj.GetAttributes
    For i = LBound(AttList) To UBound(AttList)
        ' Check for the correct attribute tag.
        If AttList(i).TextString = "SHEET NAME" Then
            AttList(i).TextString = "" & ColumnCreator.sProjectNameBox.Value
        End If
        If AttList(i).TextString = "PROJECT TITLE" Then
            AttList(i).TextString = "" & ColumnCreator.sProjectTitleBox.Value
        End If
        If AttList(i).TextString = "PROJECT ADDRESS" Then
            AttList(i).TextString = "" & ColumnCreator.sProjectAddressBox.Value
        End If
        If AttList(i).TextString = "DATE" Then
            AttList(i).TextString = "" & ColumnCreator.sDateBox.Value
        End If
        If AttList(i).TextString = "SCALE" Then
            AttList(i).TextString = "3/4'' = 1'-0''"
        End If
        If AttList(i).TextString = "DRAWN BY" Then
            AttList(i).TextString = "" & ColumnCreator.sDrawnByBox.Value
        End If
        If AttList(i).TextString = "JOB NUMBER" Then
            AttList(i).TextString = "" & ColumnCreator.sJobNoBox.Value
        End If
        If AttList(i).TextString = "SHEET_#" Then
            AttList(i).TextString = "" & ColumnCreator.sSheetBox.Value
        End If
        If AttList(i).TextString = "SUFFIX" Then
            AttList(i).TextString = "" & ColumnCreator.sSuffixBox.Value
        End If
    Next i


last_line:
' / / / / / / / / / / / / / / / / / / / / / / / / / / / / / / / / / / / /
'                          C L E A N   U P
' \ \ \ \ \ \ \ \ \ \ \ \ \ \ \ \ \ \ \ \ \ \ \ \ \ \ \ \ \ \ \ \ \ \ \ \
    ThisDrawing.ActiveDimStyle = OldDimStyle
    ThisDrawing.ActiveTextStyle = OldTextStyle
    ThisDrawing.ActiveLayer = OldLayer
    
    'Clean up objects that may be causing a lock violation
    Set MTextObject1 = Nothing
    Set MTextObject2 = Nothing
    Set objTextStyle = Nothing
    Set dimObj = Nothing
    Set LineObj = Nothing
    Set plineObj = Nothing
    Set BlockRefObj = Nothing
    Set ObjDynBlockProp = Nothing
    Set OldDimStyle = Nothing
    Set OldTextStyle = Nothing
    Set OldLayer = Nothing
    Set NewDimStyle = Nothing
    Set NewTextStyle = Nothing
    Set NewLayer = Nothing
    
    GoTo SkipErrorHandler
ErrorHandler:
    If Err.Number = -2147352567 Then 'This error occurs when the user presses the ESC key while inside the GetPoint utility
        ColumnCreator.show
        Exit Function
    ElseIf Err.Number = -2145386422 Then 'This error occurs when the path to Egnyte isn't found
        MsgBox ("Error: VBA block library not found at: " & FileToInsert & vbNewLine & vbNewLine & "Check Egnyte (Z:\) connection. Try closing and relaunching Egnyte Connect.")
        Exit Function
    ElseIf Err.Number = -2145386445 Then 'This error occurs when a block definition that doesn't exist is attempted to be inserted.
        If BlockExists = True Then
            MsgBox ("This drawing seems to be missing blocks for this VBA script. This is normal if you are using new button features on an old drawing. The block library will be re-downloaded and this script terminated." & vbNewLine & vbNewLine & "Please run the button again.")
            'Insert the block library then delete it
            FileToInsert = FileLocationPrefix & "VBA_Block_Library.dwg"
            Set BlockDwg = ThisDrawing.ModelSpace.InsertBlock(insertionPnt, FileToInsert, 1#, 1#, 1#, 0)
            BlockDwg.Delete
            Exit Function
        Else
            MsgBox ("Error: This drawing seems to be missing blocks for this VBA script despite the block library having been downloaded. The library may be missing the necessary blocks, or something mysterious has gone horribly wrong." & vbNewLine & vbNewLine & "Library location: " & FileToInsert)
            Exit Function
        End If
    Else 'Generic error message
        MsgBox ("An error occured." & vbNewLine & "error " & Err.Number & vbNewLine & Err.Description)
        Exit Function
    End If
    
SkipErrorHandler:

End Function



Public Function ChangeProp(BlockRefObj, PropName, PropValue)

    Props = BlockRefObj.GetDynamicBlockProperties
    Dim oprop As AcadDynamicBlockReferenceProperty
    
    For i = LBound(Props) To UBound(Props)
        Set oprop = Props(i) 'Get object properties from block one at a time
        If oprop.PropertyName = PropName Then 'compare to property name
            oprop.Value = PropValue 'if name matches, assign new PropValue
        End If
    'Exit For
    Next i
End Function
Public Function DrawDim(x1 As Double, y1 As Double, x2 As Double, y2 As Double, x3 As Double, y3 As Double)

    Dim dimObj As AcadDimAligned
    Dim point1(0 To 2) As Double 'first point
    Dim point2(0 To 2) As Double 'second point
    Dim location(0 To 2) As Double 'text location
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimAligned(point1, point2, location)
End Function
Public Function DrawDimSuffix(x1 As Double, y1 As Double, x2 As Double, y2 As Double, x3 As Double, y3 As Double, txt As String)

    Dim dimObj As AcadDimAligned
    Dim point1(0 To 2) As Double
    Dim point2(0 To 2) As Double
    Dim location(0 To 2) As Double
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimAligned(point1, point2, location)
    dimObj.TextSuffix = txt
    
End Function
Public Function DrawDimLin(x1 As Double, y1 As Double, x2 As Double, y2 As Double, x3 As Double, y3 As Double, angle As Double)

    Dim dimObj As AcadDimRotated
    Dim point1(0 To 2) As Double 'first point
    Dim point2(0 To 2) As Double 'second point
    Dim location(0 To 2) As Double 'text location
    
    ' Define the dimension
    point1(0) = x1#:    point1(1) = y1#:    point1(2) = 0#
    point2(0) = x2#:    point2(1) = y2#:    point2(2) = 0#
    location(0) = x3#:  location(1) = y3#:  location(2) = 0#
    
    ' Create an aligned dimension object in model space
    Set dimObj = ThisDrawing.ModelSpace.AddDimRotated(point1, point2, location, angle)
End Function
Public Function DrawDimLinSuffixLeader(x1 As Double, y1 As Double, x2 As Double, y2 As Double, x3 As Double, y3 As Double, x4 As Double, y4 As Double, txt As String, angle As Double)

    Dim dimObj As AcadDimRotated
    Dim point1(0 To 2) As Double
    Dim point2(0 To 2) As Double
    Dim location(0 To 2) As Double
    Dim txtLocation(0 To 2) As Double
    
    ' Define the dimension
    point1(0) = x1#: point1(1) = y1#: point1(2) = 0#
    point2(0) = x2#: point2(1) = y2#: point2(2) = 0#
    location(0) = x3#: location(1) = y3#: location(2) = 0#
    txtLocation(0) = x4#: txtLocation(1) = y4#: txtLocation(2) = 0#
    
    ' Create an aligned dimension object in model space
    Set dimObj = ThisDrawing.ModelSpace.AddDimRotated(point1, point2, location, angle)
    dimObj.TextMovement = acMoveTextAddLeader
    dimObj.TextPosition = txtLocation
    dimObj.TextSuffix = txt
End Function
Public Function DrawDimLinLeader(x1 As Double, y1 As Double, x2 As Double, y2 As Double, x3 As Double, y3 As Double, x4 As Double, y4 As Double, angle As Double)

    Dim dimObj As AcadDimRotated
    Dim point1(0 To 2) As Double
    Dim point2(0 To 2) As Double
    Dim location(0 To 2) As Double
    Dim txtLocation(0 To 2) As Double
    
    ' Define the dimension
    point1(0) = x1#: point1(1) = y1#: point1(2) = 0#
    point2(0) = x2#: point2(1) = y2#: point2(2) = 0#
    location(0) = x3#: location(1) = y3#: location(2) = 0#
    txtLocation(0) = x4#: txtLocation(1) = y4#: txtLocation(2) = 0#
    
    ' Create an aligned dimension object in model space
    Set dimObj = ThisDrawing.ModelSpace.AddDimRotated(point1, point2, location, angle)
    dimObj.TextMovement = acMoveTextAddLeader
    dimObj.TextPosition = txtLocation
End Function
'draws a rectangle with lower left corner at xoff, yoff with COORDINATES for far point specified
'    4_______3B
'    |       |
'    |       |
'    |_______|
'   A1       2

Public Function DrawRectangle(xA As Double, yA As Double, xB As Double, yB As Double)
    Dim plineObj As AcadLWPolyline
    Dim pts(0 To 7) As Double
    
    pts(0) = xA#:   pts(1) = yA
    pts(2) = xB#:   pts(3) = yA
    pts(4) = xB#:   pts(5) = yB
    pts(6) = xA#:   pts(7) = yB

    Set plineObj = ThisDrawing.ModelSpace.AddLightWeightPolyline(pts)
    plineObj.Closed = True

End Function
Public Function FindMax(Arr As Variant)
    Dim RetMax As Double
    RetMax = Arr(LBound(Arr)) 'initialize with first value
    
    For i = LBound(Arr) To UBound(Arr)
    If Arr(i) > RetMax Then
        RetMax = Arr(i)
    End If
    Next i
    FindMax = RetMax
End Function
